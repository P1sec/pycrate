CSvoice-HI3-IP {itu-t(0) identified-organization(4) etsi(0) securityDomain(2) lawfulIntercept(2) threeGPP(4) hi3CSvoice(18)  r14 (14) version-0 (0)}

DEFINITIONS IMPLICIT TAGS ::=

BEGIN


IMPORTS
		
	-- from ETSI HI2Operations TS 101 671, version 3.12.1
	CC-Link-Identifier,
	CommunicationIdentifier,
	LawfulInterceptionIdentifier,
	TimeStamp
		FROM HI2Operations
		{itu-t(0) identified-organization(4) etsi(0) securityDomain(2) lawfulIntercept(2) hi2(1) version18(18)}

	-- from 3GPPEps-HI3-PS TS 33.108 
	National-HI3-ASN1parameters
		FROM Eps-HI3-PS {itu-t(0) identified-organization(4) etsi(0) securityDomain(2) lawfulintercept(2) threeGPP(4) hi3eps(9) r14 (14) version-0 (0)}
		
	-- from VoIP-HI3-IMS TS 33.108
	Payload-description,
	TPDU-direction
		FROM VoIP-HI3-IMS {itu-t(0) identified-organization(4) etsi(0) securityDomain(2) lawfulIntercept(2) threeGPP(4) hi3voip(12) r14(14) version-0(0)};

-- Object Identifier Definitions

-- Security DomainId
lawfulInterceptDomainId OBJECT IDENTIFIER ::= {itu-t(0) identified-organization(4) etsi(0)
securityDomain(2) lawfulIntercept(2)}

-- Security Subdomains
threeGPPSUBDomainId OBJECT IDENTIFIER ::= {lawfulInterceptDomainId threeGPP(4)}
hi3CSvoiceDomainId OBJECT IDENTIFIER  ::= {threeGPPSUBDomainId hi3CSvoice(18) r14(14) version-0 (0)}

CSvoice-CC-PDU	::= SEQUENCE
{
 	cSvoiceLIC-header	[0] CSvoiceLIC-header,
	payload				[1] OCTET STRING,
	...
}

CSvoiceLIC-header ::= SEQUENCE
{
	hi3CSvoiceDomainId			[0]	OBJECT IDENTIFIER,  -- 3GPP IP-based delivery for CS HI3 Domain
	lIID						[1] LawfulInterceptionIdentifier OPTIONAL,
	communicationIdentifier		[2]	CommunicationIdentifier, 
		-- contents same as the contents of similar field sent in the linked IRI messages  
	ccLID						[3]	CC-Link-Identifier	OPTIONAL, 
		-- Included only if the linked IRI messages have the similar field. When included, 
		-- the content is same as the content of similar field sent in the linked IRI messages.		 
	timeStamp					[4]	TimeStamp OPTIONAL,
	sequence-number				[5]	INTEGER (0..65535),
	t-PDU-direction				[6] TPDU-direction,
	national-HI3-ASN1parameters	[7] National-HI3-ASN1parameters OPTIONAL,
		--  encoded per national requirements
	payload-description			[8] Payload-description,
		-- used to provide the codec information of the CC (as RTP payload) delivered over HI3
 	...
}


END

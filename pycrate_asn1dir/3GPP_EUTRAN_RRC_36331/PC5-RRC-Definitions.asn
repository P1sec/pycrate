PC5-RRC-Definitions DEFINITIONS AUTOMATIC TAGS ::=

BEGIN

IMPORTS
	TDD-ConfigSL-r12
FROM EUTRA-RRC-Definitions;


SBCCH-SL-BCH-Message ::= SEQUENCE {
	message					SBCCH-SL-BCH-MessageType
}

SBCCH-SL-BCH-MessageType ::=						MasterInformationBlock-SL


SBCCH-SL-BCH-Message-V2X-r14 ::= SEQUENCE {
	message					SBCCH-SL-BCH-MessageType-V2X-r14
}

SBCCH-SL-BCH-MessageType-V2X-r14 ::=				MasterInformationBlock-SL-V2X-r14


MasterInformationBlock-SL ::=		SEQUENCE {
	sl-Bandwidth-r12					ENUMERATED {
											n6, n15, n25, n50, n75, n100},
	tdd-ConfigSL-r12					TDD-ConfigSL-r12,
	directFrameNumber-r12				BIT STRING (SIZE (10)),
	directSubframeNumber-r12			INTEGER (0..9),
	inCoverage-r12						BOOLEAN,
	reserved-r12						BIT STRING (SIZE (19))
}



MasterInformationBlock-SL-V2X-r14 ::=		SEQUENCE {
	sl-Bandwidth-r14					ENUMERATED {
											n6, n15, n25, n50, n75, n100},
	tdd-ConfigSL-r14					TDD-ConfigSL-r12,
	directFrameNumber-r14				BIT STRING (SIZE (10)),
	directSubframeNumber-r14			INTEGER (0..9),
	inCoverage-r14						BOOLEAN,
	reserved-r14						BIT STRING (SIZE (27))
}



END

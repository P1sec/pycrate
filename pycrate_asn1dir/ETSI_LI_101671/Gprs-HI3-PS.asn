Gprs-HI3-PS
{itu-t(0) identified-organization(4) etsi(0) securityDomain(2) lawfulIntercept(2) hi3(2) gPRSLI(3) version3(3)}

DEFINITIONS IMPLICIT TAGS ::=

BEGIN

IMPORTS
	-- from 3GPP TS 33.108 [61]
	CC-PDU
		FROM Umts-HI3-PS
		{itu-t(0) identified-organization(4) etsi(0) securityDomain(2) lawfulintercept(2) threeGPP(4) hi3(2) r6(6) version-3(3)};

-- =============================
-- Object Identifier definitions
-- =============================

-- LawfulIntercept DomainId
lawfulInterceptDomainId OBJECT IDENTIFIER ::= {itu-t(0) identified-organization(4) etsi(0) securityDomain(2) lawfulIntercept(2)}

-- hi3 Domain
hi3GPRSLIId OBJECT IDENTIFIER ::= {lawfulInterceptDomainId hi3(2) gPRSLI(3)}
hi3GPRSLIIdOperationId OBJECT IDENTIFIER ::= {hi3GPRSLIId version3(3)}

ETSI-CC-PDU ::= SEQUENCE
{
	domainID			[0] OBJECT IDENTIFIER (hi3GPRSLIIdOperationId) OPTIONAL,
		-- Once using FTP delivery mechanism
	eTSI-CC-PDU			[1] CC-PDU,
	...
}

END -- end of Gprs-HI3-PS

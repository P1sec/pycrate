--***************************************************************************--
--                  IEEE Std 1609.2.1: CAM - RA Interface                    --
--***************************************************************************--

/** 
 * @brief NOTE: Section references in this file are to clauses in IEEE Std
 * 1609.2.1 unless indicated otherwise. Full forms of acronyms and
 * abbreviations used in this file are specified in 3.2.
 */

Ieee1609Dot2Dot1CamRaInterface {iso(1) identified-organization(3) ieee(111)
  standards-association-numbered-series-standards(2) wave-stds(1609) dot2(2)
  extension-standards(255) dot1(1) interfaces(1) cam-ra(19) major-version-2(2)
  minor-version-2(2)
}

DEFINITIONS AUTOMATIC TAGS ::= BEGIN

EXPORTS ALL;

IMPORTS
  EccP256CurvePoint,
  HashedId8,
  IValue,
  Uint8
FROM Ieee1609Dot2BaseTypes {iso(1) identified-organization(3) ieee(111)
  standards-association-numbered-series-standards(2) wave-stds(1609) dot2(2)
  base(1) base-types(2) major-version-2(2) minor-version-3(3)}
WITH SUCCESSORS
;

/**
 * @class CamRaInterfacePDU
 *
 * @brief This is the parent structure for all structures exchanged between
 * the CAM and the RA during ACPC enrollment. An overview of this structure
 * is as follows:
 *
 * @param raCamBatchRequest contains the ACPC blinded key batch request sent
 * by the RA to the CAM.
 *
 * @param camRaBatchResponse contains the CAM's response to RaCamBatchRequest.
 */
  CamRaInterfacePdu ::= CHOICE {
    raCamBatchRequest   RaCamBatchRequest,
    camRaBatchResponse  CamRaBatchResponse,
    ...
  }

/**
 * @class RaCamBatchRequest
 *
 * @brief This structure contains parameters needed to request a blinded batch
 * of keys for the EE during ACPC enrollment. An overview of this structure
 * is as follows:
 *
 * @param version contains the current version of the structure. 
 *
 * @param eeId contains the EE's ID generated by the RA for the production of
 * ACPC batch keys by the CAM. 
 *
 * @param periodList contains the list of i-periods covered by the batch.
 */
  RaCamBatchRequest ::= SEQUENCE {
    version     Uint8 (2),
    eeId        OCTET STRING (SIZE(5)),
    periodList  SEQUENCE OF IValue,
    ...
  }

/**
 * @class CamRaBatchResponse
 *
 * @brief This structure contains a blinded batch of keys for the EE during
 * ACPC enrollment. An overview of this structure is as follows:
 *
 * @param version contains the current version of the structure. 
 *
 * @param requestHash contains the hash of the corresponding request 
 * RaCamBatchRequest.
 * 
 * @param batch contains a sequence of blinded keys, each mapped to one 
 * IValue from the periodList field of the request.
 */
  CamRaBatchResponse ::= SEQUENCE {
    version      Uint8 (2),
    requestHash  HashedId8,
    batch        SEQUENCE OF BlindedKey,
    ...
  }

/**
 * @class BlindedKey
 *
 * @brief This is a blinded ACPC encryption key produced by the CAM.
 */
  BlindedKey ::= EccP256CurvePoint

END

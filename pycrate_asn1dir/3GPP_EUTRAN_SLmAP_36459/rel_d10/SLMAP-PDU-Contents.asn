-- **************************************************************
--
-- PDU definitions for SLmAP.
--
-- **************************************************************

SLMAP-PDU-Contents {
itu-t (0) identified-organization (4) etsi (0) mobileDomain (0) 
eps-Access (21) modules (3) slmap (50) version1 (1) slmap-PDU-Contents (1) }

DEFINITIONS AUTOMATIC TAGS ::= 

BEGIN

-- **************************************************************
--
-- IE parameter types from other modules.
--
-- **************************************************************

IMPORTS		
	
	ESMLC-MeasurementID,
	UL-RTOAMeasurementConfiguration,
	CriticalityDiagnostics,
	UL-RTOAMeasurements,
	Cause,
	LMU-ID,
	LMUInformation,
	ESMLC-ID,
	ESMLC-MeasurementID
	
FROM SLMAP-IEs


	PrivateIE-Container{},
	ProtocolExtensionContainer{},
	ProtocolIE-Container{},
	ProtocolIE-ContainerList{},
	ProtocolIE-ContainerPair{},
	ProtocolIE-ContainerPairList{},
	ProtocolIE-Single-Container{},
	SLMAP-PRIVATE-IES,
	SLMAP-PROTOCOL-EXTENSION,
	SLMAP-PROTOCOL-IES,
	SLMAP-PROTOCOL-IES-PAIR
FROM SLMAP-Containers


	id-ESMLC-MeasurementID,
	id-UL-RTOAMeasurementConfiguration,
	id-CriticalityDiagnostics,
	id-UL-RTOAMeasurements,
	id-Cause,
	id-LMU-ID,
	id-LMUInformation,
	id-ESMLC-ID

FROM SLMAP-Constants;


-- **************************************************************
--
-- MEASUREMENT REQUEST
--
-- **************************************************************

MeasurementRequest ::= SEQUENCE {
	protocolIEs		ProtocolIE-Container		{{MeasurementRequest-IEs}},
	...
}

MeasurementRequest-IEs SLMAP-PROTOCOL-IES ::= {
	{ ID id-ESMLC-MeasurementID					CRITICALITY reject	TYPE ESMLC-MeasurementID				PRESENCE mandatory}|
	{ ID id-UL-RTOAMeasurementConfiguration		CRITICALITY reject	TYPE UL-RTOAMeasurementConfiguration		PRESENCE mandatory},
	...
}


-- **************************************************************
--
-- MEASUREMENT RESPONSE
--
-- **************************************************************

MeasurementResponse ::= SEQUENCE {
	protocolIEs		ProtocolIE-Container		{{MeasurementResponse-IEs}},
	...
}

MeasurementResponse-IEs SLMAP-PROTOCOL-IES ::= {
	{ ID id-ESMLC-MeasurementID			CRITICALITY reject	TYPE ESMLC-MeasurementID			PRESENCE mandatory}|
	{ ID id-UL-RTOAMeasurements			CRITICALITY reject	TYPE UL-RTOAMeasurements			PRESENCE mandatory}|
	{ ID id-CriticalityDiagnostics		CRITICALITY ignore	TYPE CriticalityDiagnostics			PRESENCE optional},
	...
}


-- **************************************************************
--
-- MEASUREMENT FAILURE
--
-- **************************************************************

MeasurementFailure ::= SEQUENCE {
	protocolIEs						ProtocolIE-Container		{{MeasurementFailure-IEs}},
	...
}

MeasurementFailure-IEs SLMAP-PROTOCOL-IES ::= {
	{ ID id-ESMLC-MeasurementID			CRITICALITY reject	TYPE ESMLC-MeasurementID			PRESENCE mandatory}|
	{ ID id-Cause						CRITICALITY ignore	TYPE Cause							PRESENCE mandatory}|
	{ ID id-CriticalityDiagnostics		CRITICALITY ignore	TYPE CriticalityDiagnostics			PRESENCE optional},
	...
}


-- **************************************************************
--
-- SLM SETUP REQUEST
--
-- **************************************************************

SLMSetupRequest ::= SEQUENCE {
	protocolIEs						ProtocolIE-Container		{{SLMSetupRequest-IEs}},
	...
}

SLMSetupRequest-IEs SLMAP-PROTOCOL-IES ::= {
	{ ID id-LMU-ID				CRITICALITY ignore	TYPE LMU-ID					PRESENCE mandatory}|
	{ ID id-LMUInformation		CRITICALITY ignore	TYPE LMUInformation			PRESENCE optional},
	...
}


-- **************************************************************
--
-- SLM SETUP RESPONSE
--
-- **************************************************************

SLMSetupResponse ::= SEQUENCE {
	protocolIEs						ProtocolIE-Container		{{SLMSetupResponse-IEs}},
	...
}

SLMSetupResponse-IEs SLMAP-PROTOCOL-IES ::= {
	{ ID id-ESMLC-ID					CRITICALITY reject	TYPE ESMLC-ID						PRESENCE mandatory}|
	{ ID id-CriticalityDiagnostics		CRITICALITY ignore	TYPE CriticalityDiagnostics			PRESENCE optional},
	...
}


-- **************************************************************
--
-- SLM SETUP FAILURE
--
-- **************************************************************

SLMSetupFailure ::= SEQUENCE {
	protocolIEs						ProtocolIE-Container		{{SLMSetupFailure-IEs}},
	...
}

SLMSetupFailure-IEs SLMAP-PROTOCOL-IES ::= {
	{ ID id-Cause						CRITICALITY ignore	TYPE Cause							PRESENCE mandatory}|
	{ ID id-CriticalityDiagnostics		CRITICALITY ignore	TYPE CriticalityDiagnostics			PRESENCE optional},
	...
}



-- **************************************************************
--
-- RESET REQUEST
--
-- **************************************************************

ResetRequest ::= SEQUENCE {
	protocolIEs						ProtocolIE-Container		{{ResetRequest-IEs}},
	...
}

ResetRequest-IEs SLMAP-PROTOCOL-IES ::= {
	{ ID id-Cause				CRITICALITY ignore	TYPE Cause					PRESENCE mandatory},
	...
}


-- **************************************************************
--
-- RESET ACKNOWLEDGE
--
-- **************************************************************

ResetAcknowledge ::= SEQUENCE {
	protocolIEs						ProtocolIE-Container		{{ResetAcknowledge-IEs}},
	...
}

ResetAcknowledge-IEs SLMAP-PROTOCOL-IES ::= {
	{ ID id-CriticalityDiagnostics		CRITICALITY ignore	TYPE CriticalityDiagnostics			PRESENCE optional},
	...
}


-- **************************************************************
--
-- MEASUREMENT ABORT
--
-- **************************************************************

MeasurementAbort ::= SEQUENCE {
	protocolIEs						ProtocolIE-Container		{{MeasurementAbort-IEs}},
	...
}

MeasurementAbort-IEs SLMAP-PROTOCOL-IES ::= {
	{ ID id-ESMLC-MeasurementID			CRITICALITY reject	TYPE ESMLC-MeasurementID			PRESENCE mandatory},
	...
}


-- **************************************************************
--
-- MEASUREMENT UPDATE
--
-- **************************************************************

MeasurementUpdate ::= SEQUENCE {
	protocolIEs						ProtocolIE-Container		{{ MeasurementUpdate-IEs}},
	...
}

MeasurementUpdate-IEs SLMAP-PROTOCOL-IES ::= {
	{ ID id-ESMLC-MeasurementID					CRITICALITY reject	TYPE ESMLC-MeasurementID				PRESENCE mandatory}|
	{ ID id-UL-RTOAMeasurementConfiguration		CRITICALITY reject	TYPE UL-RTOAMeasurementConfiguration		PRESENCE mandatory},
	...
}


-- **************************************************************
--
-- ERROR INDICATION
--
-- **************************************************************

ErrorIndication ::= SEQUENCE {
	protocolIEs						ProtocolIE-Container		{{ErrorIndication-IEs}},
	...
}

ErrorIndication-IEs SLMAP-PROTOCOL-IES ::= {
	{ ID id-Cause						CRITICALITY ignore	TYPE Cause						PRESENCE optional}|
	{ ID id-CriticalityDiagnostics		CRITICALITY ignore	TYPE CriticalityDiagnostics		PRESENCE optional},
	...
}


-- **************************************************************
--
-- PRIVATE MESSAGE
--
-- **************************************************************

PrivateMessage ::= SEQUENCE {
	privateIEs		PrivateIE-Container  {{PrivateMessage-IEs}},
	...
}

PrivateMessage-IEs SLMAP-PRIVATE-IES ::= {
	...
}

END

MAPv2-Protocol --{
   --ccitt identified-organization (4) etsi (0) mobileDomain (0)
   --gsm-Network (1) modules (3) map-Protocol (4) version2 (2)}

DEFINITIONS

::=

BEGIN

IMPORTS

	OPERATION
FROM Remote-Operations-Information-Objects {
    joint-iso-itu-t remote-operations(4) informationObjects(5) version1(0)}

	updateLocation,
	cancelLocation,
	purgeMS,
	sendIdentification,
	performHandover,
	prepareHandover,
	sendEndSignal,
	processAccessSignalling,
	forwardAccessSignalling,
	performSubsequentHandover,
	prepareSubsequentHandover,
	sendAuthenticationInfo,
	checkIMEI,
	sendParameters,
	insertSubscriberData,
	deleteSubscriberData,
	reset,
	forwardCheckSS-Indication,
	restoreData
FROM MAPv2-MobileServiceOperations --{
   --ccitt identified-organization (4) etsi (0) mobileDomain (0)
   --gsm-Network (1) modules (3) map-MobileServiceOperations (5)
   --version2 (2)}

	activateTraceMode,
	deactivateTraceMode,
	traceSubscriberActivity,
	noteInternalHandover,
	sendIMSI
FROM MAPv2-OperationAndMaintenanceOperations --{
   --ccitt identified-organization (4) etsi (0) mobileDomain (0)
   --gsm-Network (1) modules (3) map-OperationAndMaintenanceOperations (6)
   --version2 (2)}

	sendRoutingInfo,
	provideRoamingNumber
FROM MAPv2-CallHandlingOperations --{
   --ccitt identified-organization (4) etsi (0) mobileDomain (0)
   --gsm-Network (1) modules (3) map-CallHandlingOperations (7)
   --version2 (2)}

	registerSS,
	eraseSS,
	activateSS,
	deactivateSS,
	interrogateSS,
	processUnstructuredSS-Data,
	processUnstructuredSS-Request,
	unstructuredSS-Request,
	unstructuredSS-Notify,
	registerPassword,
	getPassword,
	beginSubscriberActivity
FROM MAPv2-SupplementaryServiceOperations --{
   --ccitt identified-organization (4) etsi (0) mobileDomain (0)
   --gsm-Network (1) modules (3) map-SupplementaryServiceOperations (8)
   --version2 (2)}

	sendRoutingInfoForSM,
	forwardSM,
	reportSM-DeliveryStatus,
	noteSubscriberPresent,
	alertServiceCentreWithoutResult,
	alertServiceCentre,
	informServiceCentre,
	readyForSM
FROM MAPv2-ShortMessageServiceOperations --{
   --ccitt identified-organization (4) etsi (0) mobileDomain (0)
   --gsm-Network (1) modules (3) map-ShortMessageServiceOperations (9)
   --version2 (2)}
;

Supported-MAPv2-Operations OPERATION ::= {
    sendRoutingInfo |
    provideRoamingNumber |
    updateLocation |
    cancelLocation |
    purgeMS |
    sendIdentification |
    prepareHandover |
    performHandover |
    sendEndSignal |
    processAccessSignalling |
    forwardAccessSignalling |
    prepareSubsequentHandover |
    performSubsequentHandover |
    sendAuthenticationInfo |
    checkIMEI |
    sendParameters |
    insertSubscriberData |
    deleteSubscriberData |
    reset |
    forwardCheckSS-Indication |
    restoreData |
    activateTraceMode |
    deactivateTraceMode |
    traceSubscriberActivity |
    noteInternalHandover |
    sendIMSI |
    sendRoutingInfoForSM |
    forwardSM |
    reportSM-DeliveryStatus |
    noteSubscriberPresent |
    alertServiceCentreWithoutResult |
    alertServiceCentre |
    informServiceCentre |
    readyForSM |
    registerSS |
    eraseSS |
    activateSS |
    deactivateSS |
    interrogateSS |
    processUnstructuredSS-Data |
    processUnstructuredSS-Request |
    unstructuredSS-Request |
    unstructuredSS-Notify |
    registerPassword |
    getPassword |
    beginSubscriberActivity
    }


END

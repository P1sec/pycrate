-- Module TCAPMessages (Q.773:06/1997)
-- See also ITU-T Q.773 (06/1997)
-- See also the index of all ASN.1 assignments needed in this Recommendation

TCAPMessages {itu-t recommendation q 773 modules(2) messages(1) version3(3)}
DEFINITIONS IMPLICIT TAGS ::=
BEGIN

-- EXPORTS everything
-- Transaction Portion fields.
IMPORTS
  ROS{}, InvokeId
    FROM Remote-Operations-Generic-ROS-PDUs {joint-iso-itu-t
      remote-operations(4) generic-ROS-PDUs(6) version1(0)}
  OPERATION
    FROM Remote-Operations-Information-Objects {joint-iso-itu-t
      remote-operations(4) informationObjects(5) version1(0)};

TCMessage{OPERATION:Invokable, OPERATION:Returnable} ::= CHOICE {
  unidirectional  [APPLICATION 1]  Unidirectional{{Invokable}, {Returnable}},
  begin           [APPLICATION 2]  Begin{{Invokable}, {Returnable}},
  end             [APPLICATION 4]  End{{Invokable}, {Returnable}},
  continue        [APPLICATION 5]  Continue{{Invokable}, {Returnable}},
  abort           [APPLICATION 7]  Abort
}

Unidirectional{OPERATION:Invokable, OPERATION:Returnable} ::= SEQUENCE {
  dialoguePortion  DialoguePortion OPTIONAL,
  components       ComponentPortion{{Invokable}, {Returnable}}
}

Begin{OPERATION:Invokable, OPERATION:Returnable} ::= SEQUENCE {
  otid             OrigTransactionID,
  dialoguePortion  DialoguePortion OPTIONAL,
  components       ComponentPortion{{Invokable}, {Returnable}} OPTIONAL
}

End{OPERATION:Invokable, OPERATION:Returnable} ::= SEQUENCE {
  dtid             DestTransactionID,
  dialoguePortion  DialoguePortion OPTIONAL,
  components       ComponentPortion{{Invokable}, {Returnable}} OPTIONAL
}

Continue{OPERATION:Invokable, OPERATION:Returnable} ::= SEQUENCE {
  otid             OrigTransactionID,
  dtid             DestTransactionID,
  dialoguePortion  DialoguePortion OPTIONAL,
  components       ComponentPortion{{Invokable}, {Returnable}} OPTIONAL
}

Abort ::= SEQUENCE {
  dtid    DestTransactionID,
  reason  CHOICE {p-abortCause  P-AbortCause,
                  u-abortCause  DialoguePortion} OPTIONAL
}

-- NOTE - When the Abort Message is generated by the Transaction sublayer, a p-Abort Cause may be 
-- present. The u-abortCause may be generated by the component sublayer in which case it is an ABRT 
-- APDU, or by the TC-User in which case it could be either an ABRT APDU or data in some user-defined
-- abstract syntax.
DialoguePortion ::= [APPLICATION 11] EXPLICIT EXTERNAL

-- The dialogue portion carries the dialogue control PDUs as value of the external data type. The direct 
-- reference should be set to {itu-t recommendation q 773 as(1) dialogue-as(1) version1(1)} if structured 
-- dialogue is used and to {itu-t recommendation q 773 as(1) unidialogue-as(2) version1(1)} if unstructured 
-- dialogue is used.
OrigTransactionID ::= [APPLICATION 8]  OCTET STRING(SIZE (1..4))

DestTransactionID ::= [APPLICATION 9]  OCTET STRING(SIZE (1..4))

P-AbortCause ::= [APPLICATION 10]  INTEGER {
  unrecognizedMessageType(0), unrecognizedTransactionID(1),
  badlyFormattedTransactionPortion(2), incorrectTransactionPortion(3),
  resourceLimitation(4)}(0..127)

-- COMPONENT PORTION. The last field in the transaction portion of the TCAP message is the 
-- component portion. The component portion may be absent.
ComponentPortion{OPERATION:Invokable, OPERATION:Returnable} ::=
  [APPLICATION 12] 
    SEQUENCE SIZE (1..MAX) OF Component{{Invokable}, {Returnable}}

-- Component Portion fields
-- Recommendation X.880 defines four Application Protocol Data Units (APDUs) for invoking
-- operations, returning results or error, and for the rejection of invalid PDUs.
-- TCAP adds returnResultNotLast to allow for the segmentation of a result.
Component{OPERATION:Invokable, OPERATION:Returnable} ::= CHOICE {
  basicROS             ROS{{TCInvokeIdSet}, {Invokable}, {Returnable}},
  returnResultNotLast
    [7]  returnResult < ROS{{TCInvokeIdSet}, {Invokable}, {Returnable}}
}

-- pycrate, TCInvokeIdSet: unsupported conversion from a CHOICE constraint 
-- to a set of values

--TCInvokeIdSet ::= InvokeId(WITH COMPONENTS {
--                             present  (-128..127)
--                           })
TCInvokeIdSet InvokeId ::= {
    present:-128 | present:-127 | present: -126 | present: -125 |
    present:-124 | present:-123 | present: -122 | present: -121 |
    present:-120 | present:-119 | present: -118 | present: -117 |
    present:-116 | present:-115 | present: -114 | present: -113 |
    present:-112 | present:-111 | present: -110 | present: -109 |
    present:-108 | present:-107 | present: -106 | present: -105 |
    present:-104 | present:-103 | present: -102 | present: -101 |
    present:-100 | present:-99 | present: -98 | present: -97 |
    present:-96 | present:-95 | present: -94 | present: -93 |
    present:-92 | present:-91 | present: -90 | present: -89 |
    present:-88 | present:-87 | present: -86 | present: -85 |
    present:-84 | present:-83 | present: -82 | present: -81 |
    present:-80 | present:-79 | present: -78 | present: -77 |
    present:-76 | present:-75 | present: -74 | present: -73 |
    present:-72 | present:-71 | present: -70 | present: -69 |
    present:-68 | present:-67 | present: -66 | present: -65 |
    present:-64 | present:-63 | present: -62 | present: -61 |
    present:-60 | present:-59 | present: -58 | present: -57 |
    present:-56 | present:-55 | present: -54 | present: -53 |
    present:-52 | present:-51 | present: -50 | present: -49 |
    present:-48 | present:-47 | present: -46 | present: -45 |
    present:-44 | present:-43 | present: -42 | present: -41 |
    present:-40 | present:-39 | present: -38 | present: -37 |
    present:-36 | present:-35 | present: -34 | present: -33 |
    present:-32 | present:-31 | present: -30 | present: -29 |
    present:-28 | present:-27 | present: -26 | present: -25 |
    present:-24 | present:-23 | present: -22 | present: -21 |
    present:-20 | present:-19 | present: -18 | present: -17 |
    present:-16 | present:-15 | present: -14 | present: -13 |
    present:-12 | present:-11 | present: -10 | present: -9 |
    present:-8 | present:-7 | present: -6 | present: -5 |
    present:-4 | present:-3 | present: -2 | present: -1 |
    present:0 | present:1 | present: 2 | present: 3 |
    present:4 | present:5 | present: 6 | present: 7 |
    present:8 | present:9 | present: 10 | present: 11 |
    present:12 | present:13 | present: 14 | present: 15 |
    present:16 | present:17 | present: 18 | present: 19 |
    present:20 | present:21 | present: 22 | present: 23 |
    present:24 | present:25 | present: 26 | present: 27 |
    present:28 | present:29 | present: 30 | present: 31 |
    present:32 | present:33 | present: 34 | present: 35 |
    present:36 | present:37 | present: 38 | present: 39 |
    present:40 | present:41 | present: 42 | present: 43 |
    present:44 | present:45 | present: 46 | present: 47 |
    present:48 | present:49 | present: 50 | present: 51 |
    present:52 | present:53 | present: 54 | present: 55 |
    present:56 | present:57 | present: 58 | present: 59 |
    present:60 | present:61 | present: 62 | present: 63 |
    present:64 | present:65 | present: 66 | present: 67 |
    present:68 | present:69 | present: 70 | present: 71 |
    present:72 | present:73 | present: 74 | present: 75 |
    present:76 | present:77 | present: 78 | present: 79 |
    present:80 | present:81 | present: 82 | present: 83 |
    present:84 | present:85 | present: 86 | present: 87 |
    present:88 | present:89 | present: 90 | present: 91 |
    present:92 | present:93 | present: 94 | present: 95 |
    present:96 | present:97 | present: 98 | present: 99 |
    present:100 | present:101 | present: 102 | present: 103 |
    present:104 | present:105 | present: 106 | present: 107 |
    present:108 | present:109 | present: 110 | present: 111 |
    present:112 | present:113 | present: 114 | present: 115 |
    present:116 | present:117 | present: 118 | present: 119 |
    present:120 | present:121 | present: 122 | present: 123 |
    present:124 | present:125 | present: 126 | present: 127
    }

END -- TCAPMessages

-- Generated by Asnp, the ASN.1 pretty-printer of France Telecom R&D

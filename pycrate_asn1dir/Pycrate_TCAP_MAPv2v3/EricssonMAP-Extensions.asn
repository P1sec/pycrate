-- Ericsson proprietary extensions
-- EricssonMAP{ 0 identified-organization (4) etsi (0) mobileDomain (0) gsm-Network (1) modules (3) map-Protocol (4) version13 (13) }

EricssonMAP-Extensions

DEFINITIONS

IMPLICIT TAGS

::=

BEGIN

IMPORTS

	IMSI,
	IMEI,
	ISDN-AddressString,
	Ext-SS-Status,
	SignalInfo,
	TBCD-STRING
FROM MAP-CommonDataTypes {
   itu-t identified-organization (4) etsi (0) mobileDomain (0)
   gsm-Network (1) modules (3) map-CommonDataTypes (18) version13 (13)}

	RequestedEquipmentInfo
FROM MAP-MS-DataTypes {
   itu-t identified-organization (4) etsi (0) mobileDomain (0)
   gsm-Network (1) modules (3) map-MS-DataTypes (11) version13 (13)}

	ExtensionContainer,
	PrivateExtension
FROM MAP-ExtensionDataTypes {
   itu-t identified-organization (4) etsi (0) mobileDomain (0)
   gsm-Network (1) modules (3) map-ExtensionDataTypes (21) version13 (13)}
;

-- non 3GPP standard compliant extension used by Ericsson (see https://bugs.wireshark.org/bugzilla/show_bug.cgi?id=7648)
EnhancedCheckIMEI-Arg ::= SEQUENCE {
	imei			IMEI,
	requestedEquipmentInfo	RequestedEquipmentInfo OPTIONAL,
	imsi                    [PRIVATE 1] IMSI OPTIONAL,
	locationInformation     [PRIVATE 3] OCTET STRING (SIZE (1..7)) OPTIONAL,
	extensionContainer	ExtensionContainer	OPTIONAL,
	...}


-- Start of adding Private Extensions for Ericsson

-- We use NokiaMAP-Extensions which gather all extensions, including EricssonExtensionType
--EricssonExtensionSet MAP-EXTENSION ::= {
--	{ &ExtensionType; EricssonExtensionType,          &extensionId;   {1 2 826 0 1249 58 1 0} },
--	...}

EricssonExtensionType ::= CHOICE {
	isdArgType [1] IsdArgType,
	isdResType [2] IsdResType,
	dsdArgType [3] DsdArgType,
	sriArgType [4] SRIArgType,
	sriResType [5] SRIResType,
	prnArgType [6] PrnArgType,
	ulArgType  [7] UlArgType,
	rdArgType  [8] RdArgType,
	saiArgType [9] SaiArgType,
	saiResType [10] SaiResType,
	atiArgType [11] AtiArgType,
	atiResType [12] AtiResType,
	extAtiArgType [13] ExtAtiArgType
	}

IsdArgType ::= SEQUENCE (SIZE(1..50)) OF
	IsdArgData

IsdArgData ::= SEQUENCE {
	privateFeatureCode     [1] PrivateFeatureCode   OPTIONAL,
	privateFeatureData         PrivateFeatureData   OPTIONAL,
	...}

PrivateFeatureData ::= CHOICE {
	subscriptionTypeInfo           [3] SubscriptionTypeInfo,
	oickInfo                       [7] OickInfo
 }

OickInfo ::= SEQUENCE {
	ss-Status                  Ext-SS-Status,
	inCategoryKey              INCategoryKey }

INCategoryKey ::= TBCD-STRING (SIZE(1..3))

SubscriptionTypeInfo ::= SEQUENCE {
	subscriptionType     SubscriptionType }

SubscriptionType ::= OCTET STRING (SIZE(1))

IsdResType ::= SEQUENCE (SIZE(1..50)) OF
	IsdResData

IsdResData ::= SEQUENCE {
	supportedPrivateFeature [1] PrivateFeatureCode OPTIONAL,
	... }

DsdArgType ::= SEQUENCE (SIZE (1..50)) OF
	DsdArgData

DsdArgData ::= SEQUENCE {
	privateFeatureWithdraw   PrivateFeatureCode }

SRIArgType ::= SEQUENCE (SIZE(1..50)) OF
	SriArgData

SriArgData ::= SEQUENCE {
	privateFeatureCode     [1] PrivateFeatureCode   OPTIONAL,
	extraNetworkInfo       [2] ExtraSignalInfo      OPTIONAL,
	... }

SRIResType ::= SEQUENCE (SIZE(1..50)) OF
	SriResData

SriResData ::= SEQUENCE {
	privateFeatureCode     [1] PrivateFeatureCode   OPTIONAL,
	inCategoryKey          [2] INCategoryKey        OPTIONAL,
	subscriptionType       [5] SubscriptionType     OPTIONAL,
	... }

PrnArgType ::= SEQUENCE (SIZE(1..50)) OF
	PrnArgData

PrnArgData ::= SEQUENCE {
	privateFeatureCode [1] PrivateFeatureCode OPTIONAL,
	...,
	extraNetworkInfo   [2] ExtraSignalInfo OPTIONAL }

UlArgType ::= SEQUENCE (SIZE(1..50)) OF
	UlArgData

UlArgData ::= SEQUENCE {
	privateFeatureCode  [1] PrivateFeatureCode OPTIONAL,
	privateFeatureUlArgData PrivateFeatureUlArgData OPTIONAL,
	... }

PrivateFeatureUlArgData ::= CHOICE {
	adc [3] IMEI }

ExtraProtocolId ::= INTEGER { q763 (1)} (1..20)

ExtraSignalInfo ::= [PRIVATE 1] SEQUENCE {
	protocolId  ExtraProtocolId,
	signalInfo  SignalInfo }

SaiArgType ::= SEQUENCE {
	msisdn [1] NULL OPTIONAL,
	noAuthenVectorsRequested [2] NULL OPTIONAL
	}

SaiResType ::= SEQUENCE {
	msIsdn [1] ISDN-AddressString OPTIONAL
	}

AtiArgType ::= SEQUENCE {
	requestedInfoType [0] RequestedInfoType OPTIONAL
	}

AtiResType ::= SEQUENCE {
	toBeDecided [1] NULL OPTIONAL
	}

RdArgType ::= SEQUENCE {
        toBeDecidedOne [1] NULL OPTIONAL
        }

RequestedInfoType ::= SEQUENCE {
	sgsnNumber [0] NULL OPTIONAL
	}

ExtAtiArgType ::= SEQUENCE (SIZE (1..50)) OF AtiArgData

AtiArgData ::= SEQUENCE {
	privateFeatureCode [1] PrivateFeatureCode OPTIONAL,
	...}

PrivateFeatureCode ::= OCTET STRING (SIZE (1))

-- End of adding Private Extension for Ericsson

END

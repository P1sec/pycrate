MAPv2-CallHandlingOperations --{
   --ccitt identified-organization (4) etsi (0) mobileDomain (0)
   --gsm-Network (1) modules (3) map-CallHandlingOperations (7)
   --version2 (2)}

DEFINITIONS

::=

BEGIN

EXPORTS
	sendRoutingInfo,
	provideRoamingNumber
;

IMPORTS
	OPERATION
FROM Remote-Operations-Information-Objects {
    joint-iso-itu-t remote-operations(4) informationObjects(5) version1(0)}

	systemFailure,
	dataMissing,
	unexpectedDataValue,
	facilityNotSupported,
	unknownSubscriber,
	numberChanged,
	bearerServiceNotProvisioned,
	teleserviceNotProvisioned,
	noRoamingNumberAvailable,
	absentSubscriber,
	callBarred,
	forwardingViolation,
	cug-Reject
FROM MAPv2-Errors --{
   --ccitt identified-organization (4) etsi (0) mobileDomain (0)
   --gsm-Network (1) modules (3) map-Errors (10) version2 (2)}

	SendRoutingInfoArg,
	SendRoutingInfoRes,
	ProvideRoamingNumberArg
FROM MAPv2-CH-DataTypes {
   ccitt identified-organization (4) etsi (0) mobileDomain (0)
   gsm-Network (1) modules (3) map-CH-DataTypes (13) version2 (2)}

	ISDN-AddressString
FROM MAPv2-CommonDataTypes {
   ccitt identified-organization (4) etsi (0) mobileDomain (0)
   gsm-Network (1) modules (3) map-CommonDataTypes (18) version2 (2)}
;


sendRoutingInfo OPERATION ::= {				--Timer m--
	ARGUMENT
		SendRoutingInfoArg
	RESULT
		SendRoutingInfoRes
	ERRORS {
		systemFailure |
		dataMissing |
		unexpectedDataValue |
		facilityNotSupported |
		unknownSubscriber |
		numberChanged |
		-- NU1 NumberChanged must not be used in version 1
    	bearerServiceNotProvisioned |
		teleserviceNotProvisioned |
		absentSubscriber |
		callBarred |
		cug-Reject |
		-- NU1 CUG-Reject must not be used in version 1
		forwardingViolation
		}
	CODE    local: 22
	}

provideRoamingNumber OPERATION ::= {				--Timer m--
	ARGUMENT
		ProvideRoamingNumberArg
	RESULT
		ISDN-AddressString
	ERRORS {
		systemFailure |
		dataMissing |
		unexpectedDataValue |
		facilityNotSupported |
		absentSubscriber |
		noRoamingNumberAvailable
		}
	CODE    local: 4
    }

END

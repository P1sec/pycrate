MAP-ExtensionDataTypes {
   itu-t identified-organization (4) etsi (0) mobileDomain (0)
   gsm-Network (1) modules (3) map-ExtensionDataTypes (21) version16 (16)}

DEFINITIONS

IMPLICIT TAGS

::=

BEGIN

EXPORTS

	PrivateExtension,
	ExtensionContainer,
	SLR-ArgExtensionContainer
;

IMPORTS

    IsdArgExt,
    DsdArgExt,
    UlResExt,
    SS-DataExtension,
    SriExtension,
    ExtraSignalInfo,
    SriResExtension,
    CanLocArgExt,
    ATMargExt,
    DTMargExt,
    NumberPorted,
    HO-Ext,
    ATMresExt,
    AbsentSubscriberExt,
    SriForSMArgExt,
    ReportSMDelStatArgExt,
    UdlArgExt,
    RoamNotAllowedExt,
    MO-ForwardSM-ArgExt,
    ErrOlcmInfoTableExt,
    RoutingCategoryExt,
    AnyTimeModArgExt,
    AccessTypeExt,
    AccessSubscriptionListExt,
    AllowedServiceData
FROM NokiaMAP-Extensions

    EricssonExtensionType
FROM EricssonMAP-Extensions

;


-- IOC for private MAP extensions


MAP-EXTENSION ::= CLASS {
	&ExtensionType  OPTIONAL,
	&extensionId 	OBJECT IDENTIFIER }
	-- The length of the Object Identifier shall not exceed 16 octets and the
	-- number of components of the Object Identifier shall not exceed 16

-- data types

ExtensionContainer ::= SEQUENCE {
	privateExtensionList	[0]PrivateExtensionList	OPTIONAL, 
	pcs-Extensions	[1]PCS-Extensions	OPTIONAL,
	...}

SLR-ArgExtensionContainer ::= SEQUENCE {
	privateExtensionList	[0]PrivateExtensionList	OPTIONAL, 
	slr-Arg-PCS-Extensions	[1]SLR-Arg-PCS-Extensions	OPTIONAL,
	...}

PrivateExtensionList ::= SEQUENCE SIZE (1..maxNumOfPrivateExtensions) OF
				PrivateExtension

PrivateExtension ::= SEQUENCE {
	extId		MAP-EXTENSION.&extensionId
				({ExtensionSet}),
	extType		MAP-EXTENSION.&ExtensionType
				({ExtensionSet}{@extId})	OPTIONAL}

maxNumOfPrivateExtensions INTEGER ::= 10

ExtensionSet MAP-EXTENSION ::= {
    -- ExtensionSet is the set of all defined private extensions
    
    -- extensions gathered from wireshark source code: Nokia, Ericsson
    { &ExtensionType IsdArgExt,             &extensionId     {0 34 0} } |
    { &ExtensionType DsdArgExt,             &extensionId     {0 34 1} } |
    { &ExtensionType UlResExt,              &extensionId     {0 34 2} } |
    { &ExtensionType SS-DataExtension,      &extensionId     {0 34 4} } |
    { &ExtensionType SriExtension,          &extensionId     {0 34 5} } |
    { &ExtensionType ExtraSignalInfo,       &extensionId     {0 34 6} } |
    { &ExtensionType SriResExtension,       &extensionId     {0 34 7} } |
    { &ExtensionType CanLocArgExt,          &extensionId     {0 34 10} } |
    { &ExtensionType ATMargExt,             &extensionId     {0 34 11} } |
    { &ExtensionType DTMargExt,             &extensionId     {0 34 12} } |
    { &ExtensionType NumberPorted,          &extensionId     {0 34 13} } |
    { &ExtensionType HO-Ext,                &extensionId     {0 34 15} } |
    { &ExtensionType ATMresExt,             &extensionId     {0 34 16} } |
    { &ExtensionType AbsentSubscriberExt,   &extensionId     {0 34 17} } |
    { &ExtensionType SriForSMArgExt,        &extensionId     {0 34 18} } |
    { &ExtensionType ReportSMDelStatArgExt, &extensionId     {0 34 19} } |
    { &ExtensionType UdlArgExt,             &extensionId     {0 34 20} } |
    { &ExtensionType RoamNotAllowedExt,     &extensionId     {0 34 21} } |
    { &ExtensionType MO-ForwardSM-ArgExt,   &extensionId     {0 34 22} } |
    { &ExtensionType ErrOlcmInfoTableExt,   &extensionId     {0 34 23} } |
    { &ExtensionType RoutingCategoryExt,    &extensionId     {0 34 25} } |
    { &ExtensionType AnyTimeModArgExt,      &extensionId     {0 34 26} } |
    { &ExtensionType EricssonExtensionType, &extensionId     {1 2 826 0 1249 58 1 0} } |
    { &ExtensionType AccessTypeExt,         &extensionId     {1 3 12 2 1107 3 66 1 1} } |
    { &ExtensionType AccessSubscriptionListExt, &extensionId {1 3 12 2 1107 3 66 1 3} } |
    { &ExtensionType AllowedServiceData,    &extensionId     {1 3 12 2 1107 3 66 1 6} },
    ...
	}
	-- Unsupported private extensions shall be discarded if received.

PCS-Extensions ::= SEQUENCE {
	...}

SLR-Arg-PCS-Extensions ::= SEQUENCE {
	...,
	na-ESRK-Request	[0]	NULL		OPTIONAL }

END

MAPv2-CH-DataTypes {
   ccitt identified-organization (4) etsi (0) mobileDomain (0)
   gsm-Network (1) modules (3) map-CH-DataTypes (13) version2 (2)}

DEFINITIONS

IMPLICIT TAGS

::=

BEGIN

EXPORTS
	SendRoutingInfoArg,
	SendRoutingInfoRes,
	ProvideRoamingNumberArg,
	NumberOfForwarding
;

IMPORTS
	CUG-Interlock,
	ForwardingData
FROM MAPv2-SS-DataTypes {
   ccitt identified-organization (4) etsi (0) mobileDomain (0)
   gsm-Network (1) modules (3) map-SS-DataTypes (14) version2 (2)}

	ISDN-AddressString,
	ExternalSignalInfo,
	IMSI,
	LMSI
FROM MAPv2-CommonDataTypes {
   ccitt identified-organization (4) etsi (0) mobileDomain (0)
   gsm-Network (1) modules (3) map-CommonDataTypes (18) version2 (2)}
;


CUG-CheckInfo ::= SEQUENCE {
	cug-Interlock	CUG-Interlock,
	cug-OutgoingAccess	NULL			OPTIONAL,
	...}

NumberOfForwarding ::= INTEGER (1..5)

SendRoutingInfoArg ::= SEQUENCE {
	msisdn		[0] ISDN-AddressString,
	cug-CheckInfo	[1] CUG-CheckInfo	OPTIONAL,
	-- OA1 cug-CheckInfo must be absent in version 1
	numberOfForwarding	[2] NumberOfForwarding	OPTIONAL,
	networkSignalInfo	[10] ExternalSignalInfo	OPTIONAL,
	...}

SendRoutingInfoRes ::= SEQUENCE {
	imsi			IMSI,
	routingInfo	RoutingInfo,
	cug-CheckInfo	CUG-CheckInfo	OPTIONAL,
	-- OA1 cug-CheckInfo must be absent in version 1
	...}

RoutingInfo ::= CHOICE {
	roamingNumber	ISDN-AddressString,
	forwardingData	ForwardingData}

ProvideRoamingNumberArg ::= SEQUENCE {
	imsi			[0] IMSI,
	msc-Number	[1] ISDN-AddressString	OPTIONAL,
	-- OP>1 msc-Number must be present in version greater 1
	msisdn		[2] ISDN-AddressString	OPTIONAL,
	previousRoamingNumber	[3] ISDN-AddressString	OPTIONAL,
	lmsi			[4] LMSI		OPTIONAL,
	gsm-BearerCapability	[5] ExternalSignalInfo	OPTIONAL,
	networkSignalInfo	[6] ExternalSignalInfo	OPTIONAL,
	...}

END

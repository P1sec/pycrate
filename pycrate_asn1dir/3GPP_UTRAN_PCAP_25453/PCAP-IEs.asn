-- **************************************************************
--
-- Information Element Definitions
--
-- **************************************************************

PCAP-IEs {
itu-t (0) identified-organization (4) etsi (0) mobileDomain (0)
umts-Access (20) modules (3) pcap(4) version1 (1) pcap-IEs (2) }

DEFINITIONS AUTOMATIC TAGS ::=

BEGIN

IMPORTS
	maxNrOfErrors,
	maxSat,
	maxSatAlmanac,
	maxNrOfLevels,
	maxNrOfMeasNCell,
	maxNrOfMeasurements,
	maxNrOfPoints,
	maxNrOfExpInfo,
	maxNrOfSets,
	maxRateMatching,
	maxNrOfTFs,
	maxTTI-count,
	maxTS-1,
	maxCCTrCH,
	maxTF,
	maxTFC,
	maxPRACH,
	maxTrCH,
	maxTGPS,
	maxNoOfMeasurements,
	maxCellMeas,
	maxNrOfEDPCCH-PO-QUANTSTEPs,
	maxNrOfRefETFCI-PO-QUANTSTEPs,
	maxNrOfRefETFCIs,
	maxSet,
	maxGANSS,
	maxGANSSSat,
	maxGANSSSet,
	maxSgnType,
	maxGANSSSatAlmanac,
	maxGANSSClockMod,
	maxGANSS-1,
	maxNrOfIRATMeasurements,
	maxReportedGERANCells,
	maxIonGridInfo,
	maxAddPos,
	maxBeacons,
	maxBTs,
	maxWLANs,


	id-UTRAN-GPSReferenceTime,
	id-UTRAN-GPSReferenceTimeResult,
	id-GPS-UTRAN-TRU,
	id-UTRAN-GPS-DriftRate,
	id-OTDOA-AddMeasuredResultsInfo,
	id-GPS-ReferenceLocation,
	id-rxTimingDeviation768Info,
	id-rxTimingDeviation384extInfo,
	id-MeasurementValidity,
	id-ExtendedRoundTripTime,
	id-roundTripTimeInfoWithType1,
	id-AddMeasurementInfo,
	id-Extended-RNC-ID,
	id-GANSS-CommonAssistanceData,
	id-GANSS-GenericAssistanceDataList,
	id-GANSS-PositioningDataSet,
	id-GNSS-PositioningMethod,
	id-NetworkAssistedGANSSSuport,
	id-TUTRANGANSSMeasurementValueInfo,
	id-angleOfArrivalLCR,
	id-extendedTimingAdvanceLCR,
	id-additionalMeasurementInforLCR,
	id-timingAdvanceLCR-R7,
	id-rxTimingDeviationLCR,
	id-GPSReferenceTimeUncertainty,
	id-GANSS-AddIonoModelReq,
	id-GANSS-EarthOrientParaReq,
	id-GANSS-Additional-Ionospheric-Model,
	id-GANSS-Earth-Orientation-Parameters,
	id-GANSS-Additional-Time-Models,
	id-GANSS-Additional-Navigation-Models,
	id-GANSS-Additional-UTC-Models,
	id-GANSS-Auxiliary-Information,
	id-GANSS-SBAS-ID,
	id-GANSS-SBAS-IDs,
	id-GANSS-Signal-IDs,
	id-GANSS-alm-keplerianNAVAlmanac,
	id-GANSS-alm-keplerianReducedAlmanac,
	id-GANSS-alm-keplerianMidiAlmanac,
	id-GANSS-alm-keplerianGLONASS,
	id-GANSS-alm-ecefSBASAlmanac,
	id-UTRAN-GANSSReferenceTimeResult,
	id-GANSS-Reference-Time-Only,
	id-GANSS-AddADchoices,
	id-supportGANSSNonNativeADchoices,
	id-PositionDataUEbased,
	id-ganssCodePhaseAmbiguityExt,
	id-ganssIntegerCodePhaseExt,
	id-GANSScarrierPhaseRequested,
	id-GANSSMultiFreqMeasRequested,
	id-ganssReq-AddIonosphericModel,
	id-ganssReq-EarthOrientPara,
	id-ganssAddNavigationModel-req,
	id-ganssAddUTCModel-req,
	id-ganssAuxInfo-req,
	id-GANSS-AlmanacModelChoice,
	id-DGNSS-ValidityPeriod,
	id-AzimuthAndElevationLSB,
	id-completeAlmanacProvided,
	id-GPS-Week-Cycle,
	id-GANSS-Day-Cycle,
	id-ganss-Delta-T,
	id-requestedCellIDGERANMeasurements,
	id-GANSS-alm-keplerianBDSAlmanac,
	id-BDS-Ionospheric-Grid-Model,
	id-DBDS-Correction-Information,
	id-BDSIonosphericGridModel,
	id-DBDSCorrection,
	id-Confidence,
	id-ExtraDopplerInfoExtension,
	id-GANSS-Confidence,
	id-GANSS-ExtraDopplerExtension,
	id-Additional-PositioningDataSet,
	id-Additional-PositioningMethod,
	id-AddPos-MeasuredResults,
	id-AddPosSupport


FROM PCAP-Constants

	Criticality,
	ProcedureCode,
	ProtocolIE-ID,
	TransactionID,
	TriggeringMessage

FROM PCAP-CommonDataTypes

	ProtocolExtensionContainer{},
	ProtocolIE-Single-Container{},
	PCAP-PROTOCOL-EXTENSION,
	PCAP-PROTOCOL-IES

FROM PCAP-Containers;


-- **************************************************************
--
-- Accuracy Fulfilment Indicator
--
-- **************************************************************

AccuracyFulfilmentIndicator ::= ENUMERATED{
	requested-Accuracy-Fulfilled,
	requested-Accuracy-Not-Fulfilled,
	...
}


-- **************************************************************
--
-- Additional Method Type
--
-- **************************************************************

AdditionalMethodType ::= ENUMERATED {
	ue-assisted,
	ue-based,
	ue-based-preferred-but-ue-assisted-allowed,
	ue-assisted-preferred-but-ue-based-allowed,
	...
}

-- **************************************************************
--
-- Additional Positioning Measured Results
--
-- **************************************************************

AddPos-MeasuredResults ::= SEQUENCE (SIZE (1..maxAddPos)) OF AddPos-MeasuredResults-Element

AddPos-MeasuredResults-Element ::= SEQUENCE {
	timestamp					UTCTime																		OPTIONAL,
	type						CHOICE {
		barometricPressure				SEQUENCE {
			uncompensatedBarometricPressure		BaroMeasurement,
			iE-Extensions						ProtocolExtensionContainer	{ { BarometricPressure-ExtIEs } }	OPTIONAL,
			...
		},
		wlan							SEQUENCE {
			wlanMeasurementList					WLANMeasurementList,
			iE-Extensions						ProtocolExtensionContainer	{ { WLANMeasurementList-ExtIEs } }	OPTIONAL,
			...
		},
		bt								SEQUENCE {
			btMeasurementList					BTMeasurementList,
			iE-Extensions						ProtocolExtensionContainer	{ { BTMeasurementList-ExtIEs } }	OPTIONAL,
			...
		},
		mbs								SEQUENCE {
			mbsMeasurementList					MBSMeasurementList,
			iE-Extensions						ProtocolExtensionContainer	{ { MBSMeasurementList-ExtIEs } }	OPTIONAL,
			...
		},
		...
	},
	...
}

BarometricPressure-ExtIEs PCAP-PROTOCOL-EXTENSION ::= {
	...
}

WLANMeasurementList-ExtIEs PCAP-PROTOCOL-EXTENSION ::= {
	...
}

BTMeasurementList-ExtIEs PCAP-PROTOCOL-EXTENSION ::= {
	...
}

MBSMeasurementList-ExtIEs PCAP-PROTOCOL-EXTENSION ::= {
	...
}

WLANMeasurementList ::= SEQUENCE (SIZE (1..maxWLANs)) OF WLANMeasurementList-Element

WLANMeasurementList-Element ::= SEQUENCE {
	wlanBSSID					OCTET STRING (SIZE (6)),
	wlanSSID					OCTET STRING (SIZE(1..32))												OPTIONAL,
	wlanRSSI					INTEGER(-127..128)														OPTIONAL,
	wlanRTTvalue				INTEGER(0..16777215)													OPTIONAL,
	wlanRTTunits				ENUMERATED { microseconds,hundredsofnanoseconds, tensofnanoseconds, nanoseconds, tenthsofnanosecond, ...} OPTIONAL,
	wlanRTTaccuracy				INTEGER(0..255)															OPTIONAL,
	wlanAPChannelFrequency		INTEGER(0..256)															OPTIONAL,
	wlanServingFlag				BOOLEAN																	OPTIONAL,
	iE-Extensions				ProtocolExtensionContainer { { WLANMeasurementList-Element-ExtIEs } }	OPTIONAL,
	...
}

WLANMeasurementList-Element-ExtIEs PCAP-PROTOCOL-EXTENSION ::= {
	...
}

BTMeasurementList ::= SEQUENCE (SIZE (1..maxBTs)) OF BTMeasurementList-Element

BTMeasurementList-Element ::= SEQUENCE {
	btADDR					OCTET STRING (SIZE(6)),
	btRSSI					INTEGER(-127..128)														OPTIONAL,
	iE-Extensions			ProtocolExtensionContainer { { BTMeasurementList-Element-ExtIEs } }		OPTIONAL,
	...
}

BTMeasurementList-Element-ExtIEs PCAP-PROTOCOL-EXTENSION ::= {
	...
}

MBSMeasurementList ::= SEQUENCE (SIZE (1..maxBeacons)) OF MBSMeasurementList-Element

MBSMeasurementList-Element ::= SEQUENCE {
	transmitterID				INTEGER(0..32767),
	codephase					INTEGER(0..2097151),
	codephaseRMS				INTEGER(0..63),
	iE-Extensions				ProtocolExtensionContainer { { MBSMeasurementList-Element-ExtIEs } }		OPTIONAL,
	...
}

MBSMeasurementList-Element-ExtIEs PCAP-PROTOCOL-EXTENSION ::= {
	...
}

BaroMeasurement ::= INTEGER(30000..115000)

-- **************************************************************
--
-- Almanac and Satellite Health SIB
--
-- **************************************************************

AlmanacAndSatelliteHealthSIB ::=	SEQUENCE {
	gpsAlmanacAndSatelliteHealth		GPS-AlmanacAndSatelliteHealth,
	satMask								BIT STRING (SIZE (1..32)),
	lsbTOW								BIT STRING (SIZE (8)),
	iE-Extensions						ProtocolExtensionContainer { { AlmanacAndSatelliteHealthSIB-ExtIEs } }	OPTIONAL,
	...
}

AlmanacAndSatelliteHealthSIB-ExtIEs PCAP-PROTOCOL-EXTENSION ::= {
	...
}


-- **************************************************************
--
-- Cause IE
--
-- **************************************************************

Cause ::= CHOICE {
	radioNetwork			CauseRadioNetwork,
	transport				CauseTransport,
	protocol				CauseProtocol,
	misc					CauseMisc,
	...
}
CauseRadioNetwork ::= ENUMERATED {
	invalid-reference-information,
	information-temporarily-not-available,
	information-provision-not-supported-for-the-object,
	position-calculation-error-invalid-GPS-measured-results,
	...,
	position-calculation-error-invalid-CellID-measured-results,
	position-calculation-error-invalid-OTDOA-measured-results,
	position-calculation-error-AGPS-positioning-method-not-supported,
	position-calculation-error-CellID-positioning-method-not-supported,
	position-calculation-error-OTDOA-positioning-method-not-supported,
	initial-UE-position-estimate-missing,
	position-caclulation-error-invalid-UTDOA-measured-results,
	position-calculation-error-UTDOA-positioning-method-not-supported,
	position-calculation-error-UTDOA-not-supported-UTRAN-cell,
	positioning-method-not-supported,
	loss-of-contact-with-UE,
	sAS-unable-to-perform-UTDOA-positioning-within-response-time,
	location-measurement-failure,
	ue-positioning-error-Not-enough-OTDOA-cells,
	ue-positioning-error-Not-enough-GPS-Satellites,
	ue-positioning-error-Reference-Cell-not-serving-cell,
	ue-positioning-error-Not-Accomplished-GPS-Timing-of-Cell-Frames,
	ue-positioning-error-Undefined-Error,
	position-calculation-error-invalid-Galileo-measured-results,
	position-calculation-error-AGalileo-positioning-method-not-supported,
	ue-positioning-error-Not-enough-Galileo-Satellites,
	ue-positioning-error-Not-Accomplished-Galileo-Timing-of-Cell-Frames,
	ue-positioning-error-Assistance-Data-missing,
	position-calculation-error-invalid-GLONASS-measured-results,
	position-calculation-error-invalid-GANSS-measured-results,
	position-calculation-error-AGANSS-positioning-method-not-supported,
	ue-positioning-error-Not-enough-GANSS-Satellites,
	ue-positioning-error-Not-Accomplished-GANSS-Timing-of-Cell-Frames,
	position-calculation-error-invalid-BDS-measured-results,
	ue-Positioning-Error-Not-enough-BDS-Satellites,
	position-calculation-error-A-BDS-positioning-method-not-supported
}

CauseTransport ::= ENUMERATED {
	transport-resource-unavailable,
	unspecified,
	...
}

CauseProtocol ::= ENUMERATED {
	transfer-syntax-error,
	abstract-syntax-error-reject,
	abstract-syntax-error-ignore-and-notify,
	message-not-compatible-with-receiver-state,
	semantic-error,
	unspecified,
	abstract-syntax-error-falsely-constructed-message,
	...
}


CauseMisc ::= ENUMERATED {
	processing-overload,
	hardware-failure,
	o-and-m-intervention,
	unspecified,
	...
}

-- **************************************************************
--
-- Cell Id Measured Results Sets
--
-- **************************************************************

CellId-MeasuredResultsSets ::=			SEQUENCE (SIZE (1..maxNrOfMeasurements)) OF
	CellId-MeasuredResultsInfoList

CellId-MeasuredResultsInfoList ::=		SEQUENCE (SIZE (1..maxNrOfMeasNCell)) OF
	CellId-MeasuredResultsInfo

CellId-MeasuredResultsInfo ::=			SEQUENCE {
	uC-ID								UC-ID,
	uTRANAccessPointPositionAltitude	UTRANAccessPointPositionAltitude,
	ue-PositionEstimate					UE-PositionEstimate			OPTIONAL,
	roundTripTimeInfo					RoundTripTimeInfo			OPTIONAL, -- FDD only
	rxTimingDeviationInfo				RxTimingDeviationInfo		OPTIONAL, -- 3.84Mcps TDD only
	rxTimingDeviationLCRInfo			RxTimingDeviationLCRInfo	OPTIONAL, -- 1.28Mcps TDD only
	pathloss							Pathloss					OPTIONAL,
	iE-Extensions						ProtocolExtensionContainer { { CellId-MeasuredResultsInfo-ExtIEs } }		OPTIONAL,
	...
}

CellId-MeasuredResultsInfo-ExtIEs PCAP-PROTOCOL-EXTENSION ::= {
	{ ID id-rxTimingDeviation768Info	CRITICALITY reject	EXTENSION RxTimingDeviation768Info				PRESENCE optional }| -- 7.68Mcps TDD only
	{ ID id-rxTimingDeviation384extInfo	CRITICALITY reject	EXTENSION RxTimingDeviation384extInfo			PRESENCE optional }| -- 3.84Mcps TDD only
	{ ID id-roundTripTimeInfoWithType1	CRITICALITY ignore	EXTENSION RoundTripTimeInfoWithType1			PRESENCE optional }| -- FDD only
	{ ID id-AddMeasurementInfo			CRITICALITY ignore	EXTENSION AddMeasurementInfo					PRESENCE optional }|
	{ ID id-angleOfArrivalLCR			CRITICALITY ignore	EXTENSION AngleOfArrivalLCR						PRESENCE optional },
	...
}

RoundTripTimeInfo ::=					SEQUENCE {
	ue-RxTxTimeDifferenceType2			UE-RxTxTimeDifferenceType2,
	ue-PositioningMeasQuality			UE-PositioningMeasQuality,
	roundTripTime						RoundTripTime,
	iE-Extensions						ProtocolExtensionContainer { { RoundTripTimeInfo-ExtIEs } }		OPTIONAL,
	...
}

RoundTripTimeInfo-ExtIEs PCAP-PROTOCOL-EXTENSION ::= {
	{ ID id-ExtendedRoundTripTime	CRITICALITY ignore	EXTENSION ExtendedRoundTripTime					PRESENCE optional }, -- FDD only
	...
}

RoundTripTimeInfoWithType1 ::=			SEQUENCE {
	ue-RxTxTimeDifferenceType1			UE-RxTxTimeDifferenceType1,
	roundTripTime						RoundTripTime,
	extendedRoundTripTime				ExtendedRoundTripTime		OPTIONAL, -- FDD only
	iE-Extensions						ProtocolExtensionContainer { { RoundTripTimeInfoWithType1-ExtIEs } }		OPTIONAL,
	...
}

RoundTripTimeInfoWithType1-ExtIEs PCAP-PROTOCOL-EXTENSION ::= {
	...
}

UE-RxTxTimeDifferenceType2 ::=			INTEGER (0..8191)

UE-RxTxTimeDifferenceType1 ::=			INTEGER (768..1280)

UE-PositioningMeasQuality ::=			SEQUENCE {
	stdResolution						BIT STRING (SIZE (2)),
	numberOfMeasurements				BIT STRING (SIZE (3)),
	stdOfMeasurements					BIT STRING (SIZE (5)),
	iE-Extensions						ProtocolExtensionContainer { { UE-PositioningMeasQuality-ExtIEs } }		OPTIONAL,
	...
}

UE-PositioningMeasQuality-ExtIEs PCAP-PROTOCOL-EXTENSION ::= {
	...
}

RoundTripTime ::=						INTEGER (0..32766)
-- Actual value RoundTripTime = IE value * 0.0625 + 876

ExtendedRoundTripTime ::=						INTEGER (32767..103041)
-- Actual value RoundTripTime = IE value * 0.0625 + 876

UTRANAccessPointPositionAltitude ::=	SEQUENCE {
	geographicalCoordinates				GeographicalCoordinates,
	ga-AltitudeAndDirection				GA-AltitudeAndDirection																	OPTIONAL,
	iE-Extensions						ProtocolExtensionContainer { { UTRANAccessPointPositionAltitude-ExtIEs } }		OPTIONAL,
	...
}

UTRANAccessPointPositionAltitude-ExtIEs PCAP-PROTOCOL-EXTENSION ::= {
	...
}

RxTimingDeviationInfo ::=				SEQUENCE {
	rxTimingDeviation					RxTimingDeviation,
	timingAdvance						TimingAdvance,
	iE-Extensions						ProtocolExtensionContainer { { RxTimingDeviationInfo-ExtIEs } }		OPTIONAL,
	...
}

RxTimingDeviationInfo-ExtIEs PCAP-PROTOCOL-EXTENSION ::= {
	...
}

RxTimingDeviationLCRInfo ::=			SEQUENCE {
	rxTimingDeviationLCR				RxTimingDeviationLCR,
	timingAdvanceLCR					TimingAdvanceLCR,
	 -- The content of this IE shall be ignored if the id-extendedTimingAdvanceLCR IE is present.
	iE-Extensions						ProtocolExtensionContainer { { RxTimingDeviationLCRInfo-ExtIEs } }		OPTIONAL,
	...
}

RxTimingDeviationLCRInfo-ExtIEs PCAP-PROTOCOL-EXTENSION ::= {
{ ID id-extendedTimingAdvanceLCR	CRITICALITY ignore	EXTENSION ExtendedTimingAdvanceLCR					PRESENCE optional }, -- 1.28Mcps TDD only
	...
}

ExtendedTimingAdvanceLCR ::=			INTEGER (2048..8191)

RxTimingDeviation768Info ::=			SEQUENCE {
	rxTimingDeviation768				RxTimingDeviation768,
	timingAdvance768					TimingAdvance768,
	iE-Extensions						ProtocolExtensionContainer { { RxTimingDeviation768Info-ExtIEs } }		OPTIONAL,
	...
}

RxTimingDeviation768Info-ExtIEs PCAP-PROTOCOL-EXTENSION ::= {
	...
}


RxTimingDeviation384extInfo ::=			SEQUENCE {
	rxTimingDeviation384ext				RxTimingDeviation384ext,
	timingAdvance384ext					TimingAdvance384ext,
	iE-Extensions						ProtocolExtensionContainer { { RxTimingDeviation384extInfo-ExtIEs } }		OPTIONAL,
	...
}

RxTimingDeviation384extInfo-ExtIEs PCAP-PROTOCOL-EXTENSION ::= {
	...
}

AddMeasurementInfo ::= 					SEQUENCE {
	cpich-RSCP		CPICH-RSCP															OPTIONAL,
	cpich-EcNo		CPICH-EcNo															OPTIONAL,
	iE-Extensions	ProtocolExtensionContainer { { AddMeasurementInfo-ExtIEs } }		OPTIONAL,
	...
}

AddMeasurementInfo-ExtIEs PCAP-PROTOCOL-EXTENSION ::= {
	...
}

AngleOfArrivalLCR ::=					SEQUENCE {
	aOA-LCR								AOA-LCR,
	aOA-LCR-Accuracy-Class				AOA-LCR-Accuracy-Class,
	iE-Extensions						ProtocolExtensionContainer { { AngleOfArrivalLCR-ExtIEs } }		OPTIONAL,
	...
}

AngleOfArrivalLCR-ExtIEs PCAP-PROTOCOL-EXTENSION ::= {
	...
}

RxTimingDeviation ::=					INTEGER (0..8191)

RxTimingDeviationLCR ::=				INTEGER (0..511)

RxTimingDeviation768 ::=				INTEGER (0..65535)

RxTimingDeviation384ext ::=				INTEGER (0..32767)

TimingAdvance ::=						INTEGER (0..63)

TimingAdvanceLCR ::=					INTEGER (0..2047)

TimingAdvance768 ::=					INTEGER (0..511)

TimingAdvance384ext ::=					INTEGER (0..255)

Pathloss ::=							INTEGER (46..158)
-- Unit: dB; as defined in the Cell measured results IE of TS 25.331 [4]

CPICH-EcNo ::=							INTEGER (0..49)
-- According to CPICH_Ec/No in TS 25.133 [13]

CPICH-RSCP ::= 							INTEGER (-5..91)
-- According to CPICH_RSCP in TS 25.133 [13]

AOA-LCR ::=								INTEGER (0..719)-- According to mapping in TS 25.123 [14]

AOA-LCR-Accuracy-Class ::=				ENUMERATED {
											a,b,c,d,e,f,g,h, ...}

-- **************************************************************
--
-- Cell Id IRAT Measured Results Sets
--
-- **************************************************************

CellId-IRATMeasuredResultsSets ::=		SEQUENCE (SIZE (1..maxNrOfIRATMeasurements)) OF
	CellId-IRATMeasuredResultsInfoList

CellId-IRATMeasuredResultsInfoList ::=	SEQUENCE {
	gERAN-MeasuredResultsInfoList		GERAN-MeasuredResultsInfoList														OPTIONAL,
	iE-Extenstions						ProtocolExtensionContainer { { CellId-IRATMeasuredResultsInfoListExtIEs }} 	OPTIONAL,
	...
}

CellId-IRATMeasuredResultsInfoListExtIEs PCAP-PROTOCOL-EXTENSION ::= {
	...
}

GERAN-MeasuredResultsInfoList ::= 		SEQUENCE (SIZE (1..maxReportedGERANCells)) OF
	GERAN-MeasuredResultsInfo

GERAN-MeasuredResultsInfo ::=			SEQUENCE {
	gERANCellID							GERANCellGlobalID														OPTIONAL,
	gERANPhysicalCellID					GERANPhysicalCellID,
	gSM-RSSI							GSM-RSSI,
	iE-Extenstions						ProtocolExtensionContainer { { GERAN-MeasuredResultsInfo-ExtIEs }} OPTIONAL,
	...
}

GERAN-MeasuredResultsInfo-ExtIEs		PCAP-PROTOCOL-EXTENSION ::= {
	...
}

GERANCellGlobalID ::=					SEQUENCE {
	plmn-Identity						PLMN-Identity,			--As defined in TS 23.003
	locationAreaCode					BIT STRING (SIZE (16)),
	cellIdentity						BIT STRING (SIZE (16)),
	iE-Extenstions						ProtocolExtensionContainer { { GERANCellGlobalID-ExtIEs }} 			OPTIONAL,
	...
}

GERANCellGlobalID-ExtIEs				PCAP-PROTOCOL-EXTENSION ::= {
	...
}

PLMN-Identity ::=						OCTET STRING (SIZE (3))


GSM-RSSI ::=							INTEGER (0..63)

GERANPhysicalCellID ::=					SEQUENCE {
	bsic								GSM-BSIC,
	arfcn								GSM-BCCH-ARFCN
}

GSM-BSIC ::=							SEQUENCE {
	networkColourCode					BIT STRING (SIZE (3)),
	baseStationColourCode				BIT STRING (SIZE (3))
}

GSM-BCCH-ARFCN ::= 						INTEGER (0..1023)

-- **************************************************************
--
-- Cell-ID Positioning (Position Activation Request Message)
--
-- **************************************************************

CellIDPositioning ::= SEQUENCE {
	requestedCellIDMeasurements 	RequestedCellIDMeasurements,
	iE-Extensions					ProtocolExtensionContainer { { CellIDPositioning-ExtIEs } } OPTIONAL,
	...
}

CellIDPositioning-ExtIEs PCAP-PROTOCOL-EXTENSION ::= {
	{ ID id-requestedCellIDGERANMeasurements	CRITICALITY reject	EXTENSION RequestedCellIDGERANMeasurements	PRESENCE optional },
	...
}

RequestedCellIDMeasurements ::= CHOICE {
	fdd		SEQUENCE {
				roundTripTimeInfoWanted				BOOLEAN,
				pathlossWanted						BOOLEAN,
				roundTripTimeInfoWithType1Wanted	BOOLEAN,
				cpichRSCPWanted						BOOLEAN,
				cpicEcNoWanted						BOOLEAN,
				iE-Extensions						ProtocolExtensionContainer 	{ { RequestedCellIDMeasurementsFDD-ExtIEs } } OPTIONAL,
				...
				},
	tdd		SEQUENCE {
				rxTimingDeviationInfoWanted			BOOLEAN,
				pathlossWanted						BOOLEAN,
				rxTimingDeviationLCRInfoWanted		BOOLEAN,
				rxTimingDeviation768InfoWanted		BOOLEAN,
				rxTimingDeviation384extInfoWanted	BOOLEAN,
				angleOfArrivalLCRWanted				BOOLEAN,
				timingAdvanceLCRWanted				BOOLEAN,
				iE-Extensions						ProtocolExtensionContainer 	{ { RequestedCellIDMeasurementsTDD-ExtIEs } } OPTIONAL,
				...
				},
	...
}

RequestedCellIDMeasurementsFDD-ExtIEs PCAP-PROTOCOL-EXTENSION ::= {
	...
}

RequestedCellIDMeasurementsTDD-ExtIEs PCAP-PROTOCOL-EXTENSION ::= {
	...
}

RequestedCellIDGERANMeasurements ::= SEQUENCE {
	rSSIMeasurementsWanted	BOOLEAN,
	iE-Extensions			ProtocolExtensionContainer { { RequestedCellIDGERANMeasurements-ExtIEs} }	OPTIONAL,
	...
}

RequestedCellIDGERANMeasurements-ExtIEs PCAP-PROTOCOL-EXTENSION ::= {
	...
}


-- **************************************************************
--
-- Client Type
--
-- **************************************************************

ClientType ::= ENUMERATED {
	emergency-services,
	value-added-services,
	plmn-operator-services,
	lawful-intercept-services,
	plmn-operator-broadcast-services,
	plmn-operator-oam,
	plmn-operator-anonymous-statistics,
	plmn-operator-target-ms-service-support,
	...
}

-- **************************************************************
--
-- CriticalityDiagnostics
--
-- **************************************************************

CriticalityDiagnostics ::= SEQUENCE {
	procedureCode				ProcedureCode													OPTIONAL,
	triggeringMessage			TriggeringMessage												OPTIONAL,
	procedureCriticality		Criticality														OPTIONAL,
	transactionID				TransactionID													OPTIONAL,
	iEsCriticalityDiagnostics	CriticalityDiagnostics-IE-List									OPTIONAL,
	iE-Extensions				ProtocolExtensionContainer { {CriticalityDiagnostics-ExtIEs} }	OPTIONAL,
	...
}

CriticalityDiagnostics-IE-List ::= SEQUENCE (SIZE (1..maxNrOfErrors)) OF
	SEQUENCE {
		iECriticality			Criticality,
		iE-ID					ProtocolIE-ID,
		repetitionNumber		CriticalityDiagnosticsRepetition											OPTIONAL,
		messageStructure		MessageStructure															OPTIONAL,
		typeOfError				TypeOfError,
		iE-Extensions			ProtocolExtensionContainer { {CriticalityDiagnostics-IE-List-ExtIEs} }	OPTIONAL,
		...
	}

CriticalityDiagnostics-IE-List-ExtIEs PCAP-PROTOCOL-EXTENSION ::= {
	...
}

CriticalityDiagnostics-ExtIEs PCAP-PROTOCOL-EXTENSION ::= {
	...
}

CriticalityDiagnosticsRepetition ::= INTEGER (0..255)


TypeOfError ::= ENUMERATED {
	not-understood,
	missing,
	...
}

-- **************************************************************
--
-- DGPSCorrections
--
-- **************************************************************


DGPSCorrections ::=					SEQUENCE {
	gps-TOW-sec							INTEGER (0..604799),
	statusHealth						DiffCorrectionStatus,
	dgps-CorrectionSatInfoList			DGPS-CorrectionSatInfoList										OPTIONAL,
	-- not included if satelliteHealth is equal to noData or invalidData
	iE-Extensions						ProtocolExtensionContainer { { DGPSCorrections-ExtIEs } }		OPTIONAL,
	...
}

DGPSCorrections-ExtIEs PCAP-PROTOCOL-EXTENSION ::= {
	...
}


DiffCorrectionStatus ::=			ENUMERATED {
										udre-1-0, udre-0-75, udre-0-5, udre-0-3,
										udre-0-2, udre-0-1, noData, invalidData }

DGPS-CorrectionSatInfoList ::=		SEQUENCE (SIZE (1..maxSat)) OF
										DGPS-CorrectionSatInfo

DGPS-CorrectionSatInfo ::=			SEQUENCE {
	satID								INTEGER (0..63),
	iode								INTEGER (0..255),
	udre								UDRE,
	prc									PRC,
	rrc									RRC,
	iE-Extensions						ProtocolExtensionContainer { { DGPS-CorrectionSatInfo-ExtIEs } }		OPTIONAL,
	...
}

DGPS-CorrectionSatInfo-ExtIEs PCAP-PROTOCOL-EXTENSION ::= {
	{ID id-DGNSS-ValidityPeriod	CRITICALITY	ignore	EXTENSION	DGNSS-ValidityPeriod	PRESENCE	optional},
	...
}

DGNSS-ValidityPeriod ::= 			SEQUENCE {
	udreGrowthRate						UDREGrowthRate,
	udreValidityTime					UDREValidityTime,
	iE-Extensions						ProtocolExtensionContainer { { DGNSS-ValidityPeriod-ExtIEs } }		OPTIONAL,
	...
}

DGNSS-ValidityPeriod-ExtIEs PCAP-PROTOCOL-EXTENSION ::= {
	...
}

UDRE ::=							ENUMERATED {
										lessThan1,
										between1-and-4,
										between4-and-8,
										over8 }

UDREGrowthRate ::=					ENUMERATED {
										growth-1-point-5,
										growth-2,
										growth-4,
										growth-6,
										growth-8,
										growth-10,
										growth-12,
										growth-16	}

UDREValidityTime	::=					ENUMERATED {
											val-20sec,
											val-40sec,
											val-80sec,
											val-160sec,
											val-320sec,
											val-640sec,
											val-1280sec,
											val-2560sec	}

PRC ::=								INTEGER (-2047..2047)

RRC ::=								INTEGER (-127..127)

-- **************************************************************
--
-- IMEI, IMSI
--
-- **************************************************************

-- IMEI

IMEI ::=	OCTET STRING (SIZE (8))

-- IMSI

IMSI ::=	OCTET STRING (SIZE (3..8))


-- **************************************************************
--
-- UE-PositionEstimate (i.e., Geographical Area)
--
-- **************************************************************

-- UE-PositionEstimate is based on Geographical Area Description in 23.032

UE-PositionEstimate ::= CHOICE {
	point											GA-Point,
	pointWithUnCertainty							GA-PointWithUnCertainty,
	polygon											GA-Polygon,
	pointWithUncertaintyEllipse						GA-PointWithUnCertaintyEllipse,
	pointWithAltitude								GA-PointWithAltitude,
	pointWithAltitudeAndUncertaintyEllipsoid		GA-PointWithAltitudeAndUncertaintyEllipsoid,
	ellipsoidArc									GA-EllipsoidArc,
	...
}

GeographicalCoordinates ::= SEQUENCE {
	latitudeSign			ENUMERATED {north, south},
	latitude				INTEGER (0..8388607),
	longitude				INTEGER (-8388608..8388607),
	iE-Extensions			ProtocolExtensionContainer { {GeographicalCoordinates-ExtIEs} } OPTIONAL,
	...
}

GeographicalCoordinates-ExtIEs PCAP-PROTOCOL-EXTENSION ::= {
	...
}

GA-AltitudeAndDirection ::= SEQUENCE {
	directionOfAltitude		ENUMERATED {height, depth},
	altitude				INTEGER (0..32767),
	...
}

GA-EllipsoidArc ::= SEQUENCE {
	geographicalCoordinates		GeographicalCoordinates,
	innerRadius					INTEGER (0..65535),
	uncertaintyRadius			INTEGER (0..127),
	offsetAngle					INTEGER (0..179),
	includedAngle				INTEGER (0..179),
	confidence					INTEGER (0..100),
	iE-Extensions				ProtocolExtensionContainer { { GA-EllipsoidArc-ExtIEs} } OPTIONAL,
	...
}

GA-EllipsoidArc-ExtIEs PCAP-PROTOCOL-EXTENSION ::= {
	...
}

GA-Point ::= SEQUENCE {
	geographicalCoordinates		GeographicalCoordinates,
	iE-Extensions				ProtocolExtensionContainer { {GA-Point-ExtIEs} } OPTIONAL,
	...
}

GA-Point-ExtIEs PCAP-PROTOCOL-EXTENSION ::= {
	...
}

GA-PointWithAltitude ::= SEQUENCE {
	geographicalCoordinates		GeographicalCoordinates,
	altitudeAndDirection		GA-AltitudeAndDirection,
	iE-Extensions				ProtocolExtensionContainer { { GA-PointWithAltitude-ExtIEs} } OPTIONAL,
	...
}

GA-PointWithAltitude-ExtIEs PCAP-PROTOCOL-EXTENSION ::= {
	...
}

GA-PointWithAltitudeAndUncertaintyEllipsoid ::= SEQUENCE {
	geographicalCoordinates		GeographicalCoordinates,
	altitudeAndDirection		GA-AltitudeAndDirection,
	uncertaintyEllipse			GA-UncertaintyEllipse,
	uncertaintyAltitude			INTEGER (0..127),
	confidence					INTEGER (0..100),
	iE-Extensions				ProtocolExtensionContainer { { GA-PointWithAltitudeAndUncertaintyEllipsoid-ExtIEs} } OPTIONAL,
	...
}

GA-PointWithAltitudeAndUncertaintyEllipsoid-ExtIEs PCAP-PROTOCOL-EXTENSION ::= {
	...
}

GA-PointWithUnCertainty ::=SEQUENCE {
	geographicalCoordinates		GeographicalCoordinates,
	uncertaintyCode				INTEGER (0..127),
	iE-Extensions				ProtocolExtensionContainer { {GA-PointWithUnCertainty-ExtIEs} } OPTIONAL,
	...}

GA-PointWithUnCertainty-ExtIEs PCAP-PROTOCOL-EXTENSION ::= {
	...
}

GA-PointWithUnCertaintyEllipse ::= SEQUENCE {
	geographicalCoordinates		GeographicalCoordinates,
	uncertaintyEllipse			GA-UncertaintyEllipse,
	confidence					INTEGER (0..100),
	iE-Extensions				ProtocolExtensionContainer { { GA-PointWithUnCertaintyEllipse-ExtIEs} } OPTIONAL,
	...
}

GA-PointWithUnCertaintyEllipse-ExtIEs PCAP-PROTOCOL-EXTENSION ::= {
	...
}

GA-Polygon ::= SEQUENCE (SIZE (1..maxNrOfPoints)) OF
	SEQUENCE {
		geographicalCoordinates		GeographicalCoordinates,
		iE-Extensions				ProtocolExtensionContainer { {GA-Polygon-ExtIEs} } OPTIONAL,
		...
	}

GA-Polygon-ExtIEs PCAP-PROTOCOL-EXTENSION ::= {
	...
}

GA-UncertaintyEllipse ::= SEQUENCE {
	uncertaintySemi-major		INTEGER (0..127),
	uncertaintySemi-minor		INTEGER (0..127),
	orientationOfMajorAxis		INTEGER (0..89),
	...
}

-- **************************************************************
--
-- UE-PositionEstimateInfo
--
-- **************************************************************

UE-PositionEstimateInfo ::= SEQUENCE {
	referenceTimeChoice			ReferenceTimeChoice,
	ue-positionEstimate			UE-PositionEstimate,
	iE-Extensions				ProtocolExtensionContainer { { UE-PositionEstimateInfo-ExtIEs } } OPTIONAL,
	...
}

UE-PositionEstimateInfo-ExtIEs PCAP-PROTOCOL-EXTENSION ::= {
	{ID id-GPSReferenceTimeUncertainty	CRITICALITY ignore	EXTENSION GPSReferenceTimeUncertainty		PRESENCE optional}|
	{ID id-PositionDataUEbased			CRITICALITY ignore	EXTENSION PositionDataUEbased				PRESENCE optional},
	...
}

ReferenceTimeChoice ::=	CHOICE {
	utran-GPSReferenceTimeResult		UTRAN-GPSReferenceTimeResult,
	gps-ReferenceTimeOnly				INTEGER (0..604799999, ...),
	cell-Timing							Cell-Timing,
	...	,
	extension-ReferenceTimeChoice		Extension-ReferenceTimeChoice
}

Extension-ReferenceTimeChoice ::= ProtocolIE-Single-Container {{ Extension-ReferenceTimeChoice-IE }}

Extension-ReferenceTimeChoice-IE PCAP-PROTOCOL-IES ::= {
	{ ID id-UTRAN-GANSSReferenceTimeResult			CRITICALITY		ignore		TYPE	UTRAN-GANSSReferenceTimeResult		PRESENCE	mandatory}|
	{ ID id-GANSS-Reference-Time-Only				CRITICALITY		ignore		TYPE	GANSS-Reference-Time-Only			PRESENCE	mandatory}

}


Cell-Timing ::= SEQUENCE {
	sfn					INTEGER (0..4095),
	uC-ID				UC-ID,
	iE-Extensions	ProtocolExtensionContainer { { Cell-Timing-ExtIEs } }	OPTIONAL,
	...
		}

Cell-Timing-ExtIEs PCAP-PROTOCOL-EXTENSION ::= {
	...
}

GANSS-Reference-Time-Only ::= SEQUENCE {
	ganssTODmsec	INTEGER (0..3599999),
	ganssTimeID		GANSSID																OPTIONAL,
	iE-Extensions	ProtocolExtensionContainer { { GANSS-Reference-Time-Only-ExtIEs } }	OPTIONAL,
	...
}

GANSS-Reference-Time-Only-ExtIEs PCAP-PROTOCOL-EXTENSION ::= {
	...
}

PositionDataUEbased ::= SEQUENCE {
	positionData	BIT STRING (SIZE(16)),
	iE-Extensions	ProtocolExtensionContainer { { PositionDataUEbased-ExtIEs } }	OPTIONAL,
	...
}

PositionDataUEbased-ExtIEs PCAP-PROTOCOL-EXTENSION ::= {
	...
}

-- **************************************************
--
-- Position Data
--
-- **************************************************

PositionData ::= SEQUENCE {
	positioningDataDiscriminator		PositioningDataDiscriminator,
	positioningDataSet					PositioningDataSet											OPTIONAL,
-- This IE shall be present if the PositioningDataDiscriminator IE is set to the value "0000"		--
	iE-Extensions						ProtocolExtensionContainer { {PositionData-ExtIEs} } 		OPTIONAL,
	...
}

PositionData-ExtIEs PCAP-PROTOCOL-EXTENSION ::= {
	{ ID id-GANSS-PositioningDataSet			CRITICALITY ignore	EXTENSION GANSS-PositioningDataSet			PRESENCE optional}|
	{ ID id-Additional-PositioningDataSet		CRITICALITY ignore	EXTENSION Additional-PositioningDataSet		PRESENCE optional},
	...
}

GANSS-PositioningDataSet ::= SEQUENCE(SIZE(1..maxGANSSSet)) OF GANSS-PositioningMethodAndUsage

GANSS-PositioningMethodAndUsage ::= OCTET STRING (SIZE(1))

PositioningDataDiscriminator ::= BIT STRING (SIZE(4))

PositioningDataSet ::= SEQUENCE(SIZE(1..maxSet)) OF PositioningMethodAndUsage

PositioningMethodAndUsage ::= OCTET STRING (SIZE(1))

Additional-PositioningDataSet ::= SEQUENCE(SIZE(1..maxAddPos)) OF Additional-PositioningMethodAndUsage

Additional-PositioningMethodAndUsage ::= OCTET STRING (SIZE(1))


-- **************************************************************
--
-- GPS-AcquisitionAssistance:
--
-- **************************************************************


GPS-AcquisitionAssistance ::=	SEQUENCE {
	gps-TOW-1msec						INTEGER (0..604799999),
	satelliteInformationList			AcquisitionSatInfoList,
	iE-Extensions						ProtocolExtensionContainer { { GPS-AcquisitionAssistance-ExtIEs } }	OPTIONAL,
	...
}

GPS-AcquisitionAssistance-ExtIEs PCAP-PROTOCOL-EXTENSION ::= {
	{ID id-UTRAN-GPSReferenceTime		CRITICALITY ignore	EXTENSION UTRAN-GPSReferenceTime		PRESENCE optional}|
	{ID id-GPSReferenceTimeUncertainty	CRITICALITY ignore	EXTENSION GPSReferenceTimeUncertainty		PRESENCE optional}|
	{ID id-Confidence						CRITICALITY ignore	EXTENSION Confidence						PRESENCE optional},
	...
}

AcquisitionSatInfoList ::=			SEQUENCE (SIZE (1..maxSat)) OF
										AcquisitionSatInfo

AcquisitionSatInfo ::=				SEQUENCE {
	satID								INTEGER (0..63),
	doppler0thOrder						INTEGER (-2048..2047),
	extraDopplerInfo					ExtraDopplerInfo													OPTIONAL,
	codePhase							INTEGER (0..1022),
	integerCodePhase					INTEGER (0..19),
	gps-BitNumber						INTEGER (0..3),
	codePhaseSearchWindow				CodePhaseSearchWindow,
	azimuthAndElevation					AzimuthAndElevation													OPTIONAL,
	iE-Extensions						ProtocolExtensionContainer { { AcquisitionSatInfo-ExtIEs } }		OPTIONAL,
	...
}

AcquisitionSatInfo-ExtIEs PCAP-PROTOCOL-EXTENSION ::= {
	{ID id-ExtraDopplerInfoExtension		CRITICALITY ignore	EXTENSION ExtraDopplerInfoExtension		PRESENCE optional},
	...
}

ExtraDopplerInfo ::=				SEQUENCE {
	doppler1stOrder						INTEGER (-42..21),
	dopplerUncertainty					DopplerUncertainty,
	iE-Extensions						ProtocolExtensionContainer { { ExtraDopplerInfo-ExtIEs } }	OPTIONAL,
	...
}

ExtraDopplerInfo-ExtIEs PCAP-PROTOCOL-EXTENSION ::= {
	...
}

ExtraDopplerInfoExtension ::= SEQUENCE {
	doppler1stOrder					INTEGER (-42..21),
	dopplerUncertaintyExtension		DopplerUncertaintyExtension,
	iE-Extensions						ProtocolExtensionContainer { { ExtraDopplerInfoExtension-ExtIEs } }	OPTIONAL,
	...
}

ExtraDopplerInfoExtension-ExtIEs PCAP-PROTOCOL-EXTENSION ::= {
	...
}

DopplerUncertainty ::=				ENUMERATED {
										hz12-5, hz25, hz50, hz100, hz200, ...}

DopplerUncertaintyExtension ::= ENUMERATED {
										hz300, hz400, hz500, hz600, noInformation, ...}

CodePhaseSearchWindow ::=			ENUMERATED {
										w1023, w1, w2, w3, w4, w6, w8,
										w12, w16, w24, w32, w48, w64,
										w96, w128, w192 }

AzimuthAndElevation ::=				SEQUENCE {
	azimuth								INTEGER (0..31),
	elevation							INTEGER (0..7),
	iE-Extensions						ProtocolExtensionContainer { { AzimuthAndElevation-ExtIEs } }	OPTIONAL,
	...
}

AzimuthAndElevation-ExtIEs PCAP-PROTOCOL-EXTENSION ::= {
	{ID id-AzimuthAndElevationLSB		CRITICALITY	ignore	EXTENSION	AzimuthAndElevationLSB	PRESENCE	optional},
	...
}

AzimuthAndElevationLSB ::=			SEQUENCE {
	azimuthLSB							INTEGER (0..15),
	elevationLSB						INTEGER (0..15),
	iE-Extensions						ProtocolExtensionContainer { { AzimuthAndElevationLSB-ExtIEs } }	OPTIONAL,
	...
}

AzimuthAndElevationLSB-ExtIEs PCAP-PROTOCOL-EXTENSION ::= {
	...
}

Confidence ::= INTEGER(0..100)

-- **************************************************************
--
-- GANSS Elements
--
-- **************************************************************

AuxInfoGANSS-ID1 ::= SEQUENCE (SIZE(1.. maxGANSSSat)) OF AuxInfoGANSS-ID1-element

AuxInfoGANSS-ID1-element ::= SEQUENCE {
	svID				INTEGER(0..63),
	signalsAvailable	BIT STRING (SIZE(8)),
	ie-Extensions		ProtocolExtensionContainer { { AuxInfoGANSS-ID1-element-ExtIEs } }	OPTIONAL,
	...
}

AuxInfoGANSS-ID1-element-ExtIEs PCAP-PROTOCOL-EXTENSION ::= {
	...
}

AuxInfoGANSS-ID3 ::= SEQUENCE (SIZE(1.. maxGANSSSat)) OF AuxInfoGANSS-ID3-element

AuxInfoGANSS-ID3-element ::= SEQUENCE {
	svID				INTEGER(0..63),
	signalsAvailable	BIT STRING (SIZE(8)),
	channelNumber		INTEGER (-7..13),
	ie-Extensions		ProtocolExtensionContainer { { AuxInfoGANSS-ID3-element-ExtIEs } }	OPTIONAL,
	...
}

AuxInfoGANSS-ID3-element-ExtIEs PCAP-PROTOCOL-EXTENSION ::= {
	...
}

CNAVclockModel ::= SEQUENCE {
	cnavToc				BIT STRING (SIZE (11)),
	cnavTop				BIT STRING (SIZE (11)),
	cnavURA0			BIT STRING (SIZE (5)),
	cnavURA1			BIT STRING (SIZE (3)),
	cnavURA2			BIT STRING (SIZE (3)),
	cnavAf2				BIT STRING (SIZE (10)),
	cnavAf1				BIT STRING (SIZE (20)),
	cnavAf0				BIT STRING (SIZE (26)),
	cnavTgd				BIT STRING (SIZE (13)),
	cnavISCl1cp			BIT STRING (SIZE (13)) 										OPTIONAL,
	cnavISCl1cd			BIT STRING (SIZE (13))										OPTIONAL,
	cnavISCl1ca			BIT STRING (SIZE (13))										OPTIONAL,
	cnavISCl2c			BIT STRING (SIZE (13))										OPTIONAL,
	cnavISCl5i5			BIT STRING (SIZE (13)) 										OPTIONAL,
	cnavISCl5q5			BIT STRING (SIZE (13))										OPTIONAL,
	ie-Extensions		ProtocolExtensionContainer { { CNAVclockModel-ExtIEs } }	OPTIONAL,
	...
}

CNAVclockModel-ExtIEs PCAP-PROTOCOL-EXTENSION ::= {
	...
}

DeltaUT1 ::= SEQUENCE {
	b1					BIT STRING (SIZE(11)),
	b2					BIT STRING (SIZE(10)),
	ie-Extensions		ProtocolExtensionContainer { { DeltaUT1-ExtIEs } }	OPTIONAL,
	...
}

DeltaUT1-ExtIEs PCAP-PROTOCOL-EXTENSION ::= {
	...
}

DGANSS-Corrections ::= SEQUENCE {
	dGANSS-ReferenceTime			INTEGER(0..119),
	dGANSS-Information				DGANSS-Information,
	ie-Extensions					ProtocolExtensionContainer { { DGANSS-Corrections-ExtIEs } }			OPTIONAL,
	...
}

DGANSS-Corrections-ExtIEs PCAP-PROTOCOL-EXTENSION ::= {
	...
}

DGANSS-Information ::= SEQUENCE (SIZE (1..maxSgnType)) OF DGANSS-InformationItem

DGANSS-InformationItem ::= SEQUENCE {
	gANSS-SignalId						GANSS-SignalID															OPTIONAL,
	gANSS-StatusHealth					GANSS-StatusHealth,
	-- The following IE shall be present if the Status/Health IE value is not equal to "no data" or "invalid data"
	dGANSS-SignalInformation			DGANSS-SignalInformation												OPTIONAL,
	ie-Extensions		 				ProtocolExtensionContainer { { DGANSS-InformationItem-ExtIEs } }	OPTIONAL,
	...
}

DGANSS-InformationItem-ExtIEs PCAP-PROTOCOL-EXTENSION ::= {
	...
}

DGANSS-SignalInformation ::= SEQUENCE (SIZE (1..maxGANSSSat)) OF DGANSS-SignalInformationItem

DGANSS-SignalInformationItem ::= SEQUENCE {
	satId								INTEGER(0..63),
	gANSS-iod							BIT STRING (SIZE (10)),
	udre								UDRE,
	ganss-prc							INTEGER(-2047..2047),
	ganss-rrc							INTEGER(-127..127),
	ie-Extensions						ProtocolExtensionContainer { { DGANSS-SignalInformationItem-ExtIEs } }	OPTIONAL,
	...
}

DGANSS-SignalInformationItem-ExtIEs PCAP-PROTOCOL-EXTENSION ::= {
	{ID id-DGNSS-ValidityPeriod		CRITICALITY ignore	EXTENSION DGNSS-ValidityPeriod		PRESENCE optional},
	...
}

GANSS-AddClockModels ::= CHOICE {
	navClockModel			 		NAVclockModel,
	cnavClockModel			 		CNAVclockModel,
	glonassClockModel		 		GLONASSclockModel,
	sbasClockModel			 		SBASclockModel,
	...,
	bDSClockModel					BDSClockModel
	}

GANSS-AddOrbitModels ::= CHOICE {
	navKeplerianSet	 				NavModel-NAVKeplerianSet,
	cnavKeplerianSet				NavModel-CNAVKeplerianSet,
	glonassECEF						NavModel-GLONASSecef,
	sbasECEF						NavModel-SBASecef,
	...,
	bDSKeplerianSet					NavModel-BDSKeplerianSet
	}

GANSS-Additional-Ionospheric-Model ::= SEQUENCE {
	dataID								BIT STRING (SIZE(2)),
	alpha-beta-parameters				GPS-Ionospheric-Model,
	ie-Extensions						ProtocolExtensionContainer { { GANSS-Additional-Ionospheric-Model-ExtIEs } }	OPTIONAL,
	...
}

GANSS-Additional-Ionospheric-Model-ExtIEs PCAP-PROTOCOL-EXTENSION ::= {
	...
}

GANSS-Additional-Navigation-Models ::= SEQUENCE {
	non-broadcastIndication		ENUMERATED { true }																	OPTIONAL,
	ganssSatInfoNavList			Ganss-Sat-Info-AddNavList,
	ie-Extensions				ProtocolExtensionContainer { { GANSS-Additional-Navigation-Models-ExtIEs } } OPTIONAL,
	...
}

GANSS-Additional-Navigation-Models-ExtIEs PCAP-PROTOCOL-EXTENSION ::= {
	...
}

GANSS-Additional-Time-Models ::= SEQUENCE (SIZE (1..maxGANSS-1)) OF GANSS-Time-Model

GANSS-Additional-UTC-Models ::= CHOICE {
	utcModel1			UTCmodelSet1,
	utcModel2			UTCmodelSet2,
	utcModel3			UTCmodelSet3,
	...,
	utcModel4			UTCmodelSet4
}

GANSS-ALM-BDSKeplericanset ::= SEQUENCE {
	satellite-Information-BDS-KP-List	Satellite-Information-BDS-KP-List,
	ie-Extensions						ProtocolExtensionContainer { { GANSS-ALM-BDSKeplericanset-ExtIEs } }	OPTIONAL,
	...
}

GANSS-ALM-BDSKeplericanset-ExtIEs PCAP-PROTOCOL-EXTENSION ::= {
	...
}

Satellite-Information-BDS-KP-List ::= SEQUENCE (SIZE (1..maxGANSSSatAlmanac)) OF Satellite-Information-BDS-KP-Item

Satellite-Information-BDS-KP-Item ::= SEQUENCE {
	sVID-BDS					INTEGER (0..63),
	tOA-BDS						BIT STRING( SIZE(8) ),
	a21-BDS						BIT STRING( SIZE(24) ),
	e-BDS						BIT STRING( SIZE(17) ),
	omg-lower-BDS				BIT STRING( SIZE(24) ),
	m0-BDS						BIT STRING( SIZE(24) ),
	omg-0-BDS					BIT STRING( SIZE(24) ),
	omg-upper-BDS				BIT STRING( SIZE(17) ),
	delta-i-BDS					BIT STRING( SIZE(16) ),
	a0-BDS						BIT STRING( SIZE(11) ),
	a1-BDS						BIT STRING( SIZE(11) ),
-- The following IE is mandatory present if the sVID-BDS is between 0 and 29 and not needed otherwise.
	hea-BDS						BIT STRING( SIZE(9) )					OPTIONAL,
	ie-Extensions				ProtocolExtensionContainer { { Satellite-Information-BDS-KP-Item-ExtIEs } }	OPTIONAL,
	...
}

Satellite-Information-BDS-KP-Item-ExtIEs PCAP-PROTOCOL-EXTENSION ::= {
	...
}

GANSS-ALM-ECEFsbasAlmanacSet ::= SEQUENCE {
	sat-info-SBASecefList		GANSS-SAT-Info-Almanac-SBASecefList,
	ie-Extensions		 		ProtocolExtensionContainer { { GANSS-ALM-ECEFsbasAlmanacSet-ExtIEs } }		OPTIONAL,
	...
}

GANSS-ALM-ECEFsbasAlmanacSet-ExtIEs PCAP-PROTOCOL-EXTENSION ::= {
	...
}


GANSS-ALM-GlonassAlmanacSet ::= SEQUENCE {
	sat-info-GLOkpList			GANSS-SAT-Info-Almanac-GLOkpList,
	ie-Extensions		 		ProtocolExtensionContainer { { GANSS-ALM-GlonassAlmanacSet-ExtIEs } }		OPTIONAL,
	...
}

GANSS-ALM-GlonassAlmanacSet-ExtIEs PCAP-PROTOCOL-EXTENSION ::= {
	...
}


GANSS-ALM-MidiAlmanacSet ::= SEQUENCE {
	t-oa						INTEGER (0..255),
	sat-info-MIDIkpList			GANSS-SAT-Info-Almanac-MIDIkpList,
	ie-Extensions		 		ProtocolExtensionContainer { { GANSS-ALM-MidiAlmanacSet-ExtIEs } }		OPTIONAL,
	...
}

GANSS-ALM-MidiAlmanacSet-ExtIEs PCAP-PROTOCOL-EXTENSION ::= {
	...
}

GANSS-ALM-NAVKeplerianSet ::= SEQUENCE {
	t-oa						INTEGER (0..255),
	sat-info-NAVkpList			GANSS-SAT-Info-Almanac-NAVkpList,
	ie-Extensions		 		ProtocolExtensionContainer { { GANSS-ALM-NAVKeplerianSet-ExtIEs } }		OPTIONAL,
	...
}

GANSS-ALM-NAVKeplerianSet-ExtIEs PCAP-PROTOCOL-EXTENSION ::= {
	...
}


GANSS-ALM-ReducedKeplerianSet ::= SEQUENCE {
	t-oa						INTEGER (0..255),
	sat-info-REDkpList			GANSS-SAT-Info-Almanac-REDkpList,
	ie-Extensions		 		ProtocolExtensionContainer { { GANSS-ALM-ReducedKeplerianSet-ExtIEs } }		OPTIONAL,
	...
}

GANSS-ALM-ReducedKeplerianSet-ExtIEs PCAP-PROTOCOL-EXTENSION ::= {
	...
}

GANSS-AlmanacAndSatelliteHealth ::= SEQUENCE {
	weekNumber				INTEGER(0..255),
	gANSS-AlmanacModel		GANSS-AlmanacModel,
	ie-Extensions			ProtocolExtensionContainer { { GANSS-AlmanacAndSatelliteHealth-ExtIEs } }			OPTIONAL,
	...
}

GANSS-AlmanacAndSatelliteHealth-ExtIEs PCAP-PROTOCOL-EXTENSION ::= {
	{ID id-completeAlmanacProvided		CRITICALITY	ignore	EXTENSION	CompleteAlmanacProvided PRESENCE	optional},
	...
}

GANSS-AlmanacModel ::= CHOICE {
	gANSS-keplerianParameters			GANSS-KeplerianParametersAlm,
	...,
	extension-GANSS-AlmanacModel		Extension-GANSS-AlmanacModel
}

Extension-GANSS-AlmanacModel ::= ProtocolIE-Single-Container {{ Extension-GANSS-AlmanacModel-IE }}

Extension-GANSS-AlmanacModel-IE PCAP-PROTOCOL-IES ::= {
	{ ID id-GANSS-alm-keplerianNAVAlmanac			CRITICALITY ignore	TYPE GANSS-ALM-NAVKeplerianSet			PRESENCE mandatory}|
	{ ID id-GANSS-alm-keplerianReducedAlmanac		CRITICALITY ignore	TYPE GANSS-ALM-ReducedKeplerianSet		PRESENCE mandatory}|
	{ ID id-GANSS-alm-keplerianMidiAlmanac			CRITICALITY ignore	TYPE GANSS-ALM-MidiAlmanacSet			PRESENCE mandatory}|
	{ ID id-GANSS-alm-keplerianGLONASS				CRITICALITY ignore	TYPE GANSS-ALM-GlonassAlmanacSet			PRESENCE mandatory}|
	{ ID id-GANSS-alm-ecefSBASAlmanac				CRITICALITY ignore	TYPE GANSS-ALM-ECEFsbasAlmanacSet		PRESENCE mandatory}|
	{ ID id-GANSS-alm-keplerianBDSAlmanac			CRITICALITY ignore	TYPE GANSS-ALM-BDSKeplericanset			PRESENCE mandatory}
}


GANSS-Auxiliary-Information ::= CHOICE {
	ganssID1	AuxInfoGANSS-ID1, 	-- This choice may only be present if GANSS ID indicates Modernized GPS
	ganssID3	AuxInfoGANSS-ID3, 	-- This choice may only be present if GANSS ID indicates GLONASS
	...
}

GANSS-AzimuthAndElevation ::= SEQUENCE {
	azimuth						INTEGER(0..31),
	-- applicable range of elevation is 0..7. Values 8-75 shall not be used.
	elevation					INTEGER(0..75),
	ie-Extensions				ProtocolExtensionContainer { { GANSS-AzimuthAndElevation-ExtIEs } }	OPTIONAL,
	...
}

GANSS-AzimuthAndElevation-ExtIEs PCAP-PROTOCOL-EXTENSION ::= {
	{ID id-AzimuthAndElevationLSB		CRITICALITY	ignore	EXTENSION	AzimuthAndElevationLSB	PRESENCE	optional},
	...
}

GANSS-Clock-Model ::= SEQUENCE (SIZE (1..maxGANSSClockMod)) OF GANSS-SatelliteClockModelItem

GANSS-CommonAssistanceData ::= SEQUENCE {
	ganss-Reference-Time				GANSS-Reference-Time										OPTIONAL,
	ganss-Ionospheric-Model				GANSS-Ionospheric-Model										OPTIONAL,
	ganss-Reference-Location			GANSS-Reference-Location									OPTIONAL,
	ie-Extensions						ProtocolExtensionContainer { { GANSS-CommonAssistanceData-ExtIEs } }	OPTIONAL,
	...
}

GANSS-CommonAssistanceData-ExtIEs PCAP-PROTOCOL-EXTENSION ::= {
	{ ID id-GANSS-Additional-Ionospheric-Model		CRITICALITY ignore	EXTENSION GANSS-Additional-Ionospheric-Model	PRESENCE optional }|
	{ ID id-GANSS-Earth-Orientation-Parameters		CRITICALITY ignore	EXTENSION GANSS-Earth-Orientation-Parameters	PRESENCE optional },
	...
}


GANSS-Data-Bit-Assistance ::= SEQUENCE {
	ganssTod							INTEGER (0..59,...),
	dataBitAssistancelist				GANSS-DataBitAssistanceList,
	ie-Extensions						ProtocolExtensionContainer { { GANSS-Data-Bit-Assistance-ExtIEs } }	OPTIONAL,
	...
}

GANSS-Data-Bit-Assistance-ExtIEs PCAP-PROTOCOL-EXTENSION ::= {
	...
}

GANSS-DataBitAssistanceList ::= SEQUENCE (SIZE (1..maxGANSSSat)) OF GANSS-DataBitAssistanceItem

GANSS-DataBitAssistanceItem ::= SEQUENCE {
	satId							INTEGER(0..63),
	dataBitAssistanceSgnList		GANSS-DataBitAssistanceSgnList,
	ie-Extensions					ProtocolExtensionContainer { { GANSS-DataBitAssistanceItem-ExtIEs } }	OPTIONAL,
	...
}

GANSS-DataBitAssistanceItem-ExtIEs PCAP-PROTOCOL-EXTENSION ::= {
	...
}

GANSS-DataBitAssistanceSgnList ::= SEQUENCE (SIZE (1..maxSgnType)) OF GANSS-DataBitAssistanceSgnItem


GANSS-DataBitAssistanceSgnItem ::= SEQUENCE {
	ganss-SignalId			GANSS-SignalID,
	ganssDataBits			BIT STRING (SIZE (1..1024)),
	ie-Extensions			ProtocolExtensionContainer { { GANSS-DataBitAssistanceSgnItem-ExtIEs } }	OPTIONAL,
	...
}

GANSS-DataBitAssistanceSgnItem-ExtIEs PCAP-PROTOCOL-EXTENSION ::= {
	...
}

GANSS-Earth-Orientation-Parameters ::= SEQUENCE {
	teop				BIT STRING (SIZE (16)),
	pmX					BIT STRING (SIZE (21)),
	pmXdot				BIT STRING (SIZE (15)),
	pmY					BIT STRING (SIZE (21)),
	pmYdot				BIT STRING (SIZE (15)),
	deltaUT1			BIT STRING (SIZE (31)),
	deltaUT1dot			BIT STRING (SIZE (19)),
	ie-Extensions		ProtocolExtensionContainer { { GANSS-Earth-Orientation-Parameters-ExtIEs } }	OPTIONAL,
	...
}

GANSS-Earth-Orientation-Parameters-ExtIEs PCAP-PROTOCOL-EXTENSION ::= {
	...
}


GANSS-ExtraDoppler ::= SEQUENCE {
	dopplerFirstOrder			INTEGER(-42..21),
	dopplerUncertainty			ENUMERATED{dH40,dH20,dH10,dH5,dH2-5},
	ie-Extensions				ProtocolExtensionContainer { { GANSS-ExtraDoppler-ExtIEs } }	OPTIONAL,
	...
}

GANSS-ExtraDoppler-ExtIEs PCAP-PROTOCOL-EXTENSION ::= {
	...
}

GANSS-ExtraDopplerExtension ::= SEQUENCE {
	dopplerFirstOrder				INTEGER(-42..21),
	dopplerUncertaintyExtension	ENUMERATED{dH60,dH80,dH100,dH120,noInformation},
	ie-Extensions					ProtocolExtensionContainer { { GANSS-ExtraDopplerExtension-ExtIEs } }	OPTIONAL,
	...
}

GANSS-ExtraDopplerExtension-ExtIEs PCAP-PROTOCOL-EXTENSION ::= {
	...
}

GANSS-GenericAssistanceDataList ::= SEQUENCE (SIZE (1..maxGANSS)) OF GANSSGenericAssistanceData

GANSSGenericAssistanceData ::= SEQUENCE{
	ganssId	GANSSID	OPTIONAL,
	ganss-Real-Time-Integrity	GANSS-Real-Time-Integrity	OPTIONAL,
	ganss-DataBitAssistance	GANSS-Data-Bit-Assistance	OPTIONAL,
	dganss-Corrections	DGANSS-Corrections	OPTIONAL,
	ganss-AlmanacAndSatelliteHealth	GANSS-AlmanacAndSatelliteHealth	OPTIONAL,
	ganss-ReferenceMeasurementInfo	GANSS-ReferenceMeasurementInfo	OPTIONAL,
	ganss-UTC-Model	GANSS-UTC-Model	OPTIONAL,
	ganss-Time-Model	GANSS-Time-Model	OPTIONAL,
	ganss-Navigation-Model	GANSS-Navigation-Model	OPTIONAL,
	ie-Extensions	ProtocolExtensionContainer { { GANSSGenericAssistance-ExtIEs } }	OPTIONAL,
	...
}

GANSSGenericAssistance-ExtIEs PCAP-PROTOCOL-EXTENSION ::= {
	{ ID id-GANSS-Additional-Time-Models			CRITICALITY ignore	EXTENSION GANSS-Additional-Time-Models			PRESENCE optional }|
	{ ID id-GANSS-Additional-Navigation-Models		CRITICALITY ignore	EXTENSION GANSS-Additional-Navigation-Models		PRESENCE optional }|
	{ ID id-GANSS-Additional-UTC-Models				CRITICALITY ignore	EXTENSION GANSS-Additional-UTC-Models			PRESENCE optional }|
	{ ID id-GANSS-Auxiliary-Information				CRITICALITY ignore	EXTENSION GANSS-Auxiliary-Information			PRESENCE optional }|
	-- the following IE shall be present if ‘GANSSID’ in ‘GANSSGenericAssistanceData’ is ‘0’ (SBAS)
	{ ID id-GANSS-SBAS-ID							CRITICALITY ignore	EXTENSION GANSS-SBAS-ID				PRESENCE optional }|
	{ ID id-BDS-Ionospheric-Grid-Model				CRITICALITY ignore	EXTENSION BDS-Ionospheric-Grid-Model			PRESENCE optional }|
	{ ID id-DBDS-Correction-Information				CRITICALITY ignore	EXTENSION DBDS-Correction-Information			PRESENCE optional },
	...
}

BDS-Ionospheric-Grid-Model ::= SEQUENCE {
	bDS-Reference-Time						BDS-Reference-Time,
	bDS-Ionospheric-Grid-Information		BDS-Ionospheric-Grid-Information,
	ie-Extensions		ProtocolExtensionContainer { { BDS-Ionospheric-Grid-Model-ExtIEs } } OPTIONAL,
	...
}

BDS-Ionospheric-Grid-Model-ExtIEs PCAP-PROTOCOL-EXTENSION ::= {
	...
}

BDS-Reference-Time ::= INTEGER(0..3570) -- by step of 30

BDS-Ionospheric-Grid-Information ::= SEQUENCE(SIZE(1.. maxIonGridInfo)) OF SEQUENCE {
	iGP-number-BDS				INTEGER (1..320),
	vertical-Delay-BDS			BIT STRING ( SIZE(9)),
	gIVEI-BDS					BIT STRING ( SIZE(4)),
	ie-Extensions				ProtocolExtensionContainer { { BDS-Ionospheric-Grid-Information-ExtIEs } }	OPTIONAL,
	...
}

BDS-Ionospheric-Grid-Information-ExtIEs PCAP-PROTOCOL-EXTENSION ::= {
	...
}

DBDS-Correction-Information ::= SEQUENCE {
	bDS-Reference-Time			BDS-Reference-Time,
	dBDS-Information			DBDS-Information,
	ie-Extensions				ProtocolExtensionContainer { { DBDS-Correction-Information-ExtIEs } }	OPTIONAL,
	...
}

DBDS-Correction-Information-ExtIEs PCAP-PROTOCOL-EXTENSION ::= {
	...
}

DBDS-Information ::= SEQUENCE(SIZE(1..maxSgnType)) OF SEQUENCE {
	dBDS-Signal-ID				GANSSID					OPTIONAL,
	dGANSS-Signal-Information	DGANSS-Signal-Information,
	ie-Extensions				ProtocolExtensionContainer { { DBDS-Information-ExtIEs } }	OPTIONAL,
	...
}

DBDS-Information-ExtIEs PCAP-PROTOCOL-EXTENSION ::= {
	...
}

DGANSS-Signal-Information ::= SEQUENCE(SIZE(1.. maxGANSSSat)) OF SEQUENCE {
	sat-ID-BDS					INTEGER(0..63),
	uDREI-BDS					INTEGER(0..15),
	rURAI-BDS					INTEGER(0..15),
	delta-t-BDS					BIT STRING (SIZE (13)),
	ie-Extensions				ProtocolExtensionContainer { { DGANSS-Signal-Information-ExtIEs } }	OPTIONAL,
	...
}

DGANSS-Signal-Information-ExtIEs PCAP-PROTOCOL-EXTENSION ::= {
	...
}

GANSS-GenericMeasurementInfo ::= SEQUENCE(SIZE(1..maxGANSS)) OF SEQUENCE {
	ganssId						GANSSID																		OPTIONAL,
	ganssMeasurementSignalList	GANSSMeasurementSignalList,
	ie-Extensions				ProtocolExtensionContainer { { GANSS-GenericMeasurementInfo-ExtIEs } }	OPTIONAL,
	...
}

GANSS-GenericMeasurementInfo-ExtIEs PCAP-PROTOCOL-EXTENSION ::= {
	...
}

GANSSID ::= SEQUENCE {
	ganss-ID			INTEGER(0..7),
	ie-Extensions		ProtocolExtensionContainer { { GANSSID-ExtIEs } } OPTIONAL,
	...
}

GANSSID-ExtIEs PCAP-PROTOCOL-EXTENSION ::= {
	...
}

GANSSMeasurementSignalList ::= SEQUENCE (SIZE (1..maxSgnType)) OF SEQUENCE {
	ganssSignalId						GANSS-SignalID						OPTIONAL,
	ganssCodePhaseAmbiguity				INTEGER (0..31)						OPTIONAL,
	ganssMeasurementParameters			GANSS-MeasurementParameters,
	ie-Extensions						ProtocolExtensionContainer { { GANSSMeasurementSignalList-ExtIEs } } 	OPTIONAL,
	...

}

GANSSMeasurementSignalList-ExtIEs PCAP-PROTOCOL-EXTENSION ::= {
	{ID id-ganssCodePhaseAmbiguityExt	CRITICALITY	ignore	EXTENSION	GanssCodePhaseAmbiguityExt PRESENCE	optional},
	...
}

GanssCodePhaseAmbiguityExt ::= SEQUENCE {
	ganssCodePhaseAmbiguity-ext			INTEGER (32..127),
	ie-Extensions						ProtocolExtensionContainer { { GanssCodePhaseAmbiguityExt-ExtIEs } } 			OPTIONAL,
	...
}

GanssCodePhaseAmbiguityExt-ExtIEs PCAP-PROTOCOL-EXTENSION ::= {
	...
}


GANSS-Ionospheric-Model ::= SEQUENCE {
	alpha-zero-ionos					BIT STRING (SIZE (11)),
	alpha-one-ionos						BIT STRING (SIZE (11)),
	alpha-two-ionos						BIT STRING (SIZE (14)),
	gANSS-IonosphereRegionalStormFlags	GANSS-IonosphereRegionalStormFlags						OPTIONAL,
	ie-Extensions						ProtocolExtensionContainer { { GANSS-Ionospheric-Model-ExtIEs } }	OPTIONAL,
	...
}

GANSS-Ionospheric-Model-ExtIEs PCAP-PROTOCOL-EXTENSION ::= {
	...
}

GANSS-IonosphereRegionalStormFlags ::= SEQUENCE {
	storm-flag-one						BOOLEAN,
	storm-flag-two						BOOLEAN,
	storm-flag-three					BOOLEAN,
	storm-flag-four						BOOLEAN,
	storm-flag-five						BOOLEAN,
	ie-Extensions						ProtocolExtensionContainer { { GANSS-IonosphereRegionalStormFlags-ExtIEs } } OPTIONAL,
	...
}

GANSS-IonosphereRegionalStormFlags-ExtIEs PCAP-PROTOCOL-EXTENSION ::= {
	...
}

GANSS-KeplerianParametersAlm ::= SEQUENCE {
	t-oa								INTEGER(0..1023),
	iod-a								INTEGER(0..15),
	gANSS-SatelliteInformationKP		GANSS-SatelliteInformationKP,
	ie-Extensions		 				ProtocolExtensionContainer { { GANSS-KeplerianParametersAlm-ExtIEs } }		OPTIONAL,
	...
}

GANSS-KeplerianParametersAlm-ExtIEs PCAP-PROTOCOL-EXTENSION ::= {
	...
}

GANSS-KeplerianParametersOrb ::= SEQUENCE {
	toe-nav								BIT STRING (SIZE (14)),
	ganss-omega-nav						BIT STRING (SIZE (32)),
	delta-n-nav							BIT STRING (SIZE (16)),
	m-zero-nav							BIT STRING (SIZE (32)),
	omegadot-nav						BIT STRING (SIZE (24)),
	ganss-e-nav							BIT STRING (SIZE (32)),
	idot-nav							BIT STRING (SIZE (14)),
	a-sqrt-nav							BIT STRING (SIZE (32)),
	i-zero-nav							BIT STRING (SIZE (32)),
	omega-zero-nav						BIT STRING (SIZE (32)),
	c-rs-nav							BIT STRING (SIZE (16)),
	c-is-nav							BIT STRING (SIZE (16)),
	c-us-nav							BIT STRING (SIZE (16)),
	c-rc-nav							BIT STRING (SIZE (16)),
	c-ic-nav 							BIT STRING (SIZE (16)),
	c-uc-nav							BIT STRING (SIZE (16)),
	ie-Extensions		 				ProtocolExtensionContainer { { GANSS-KeplerianParametersOrb-ExtIEs } }		OPTIONAL,
	...
}

GANSS-KeplerianParametersOrb-ExtIEs PCAP-PROTOCOL-EXTENSION ::= {
	...
}

GANSS-MeasurementParameters ::= SEQUENCE(SIZE(1..maxGANSSSat)) OF GANSS-MeasurementParametersItem

GANSS-MeasurementParametersItem ::= SEQUENCE {
	satId						INTEGER(0..63),
	cToNzero					INTEGER(0..63),
	multipathIndicator			ENUMERATED{nM,low,medium,high},
	carrierQualityIndication	BIT STRING(SIZE(2))																OPTIONAL,
	ganssCodePhase				INTEGER(0..2097151),
	ganssIntegerCodePhase		INTEGER(0..63)																	OPTIONAL,
	codePhaseRmsError			INTEGER(0..63),
	doppler						INTEGER(-32768..32767),
	adr							INTEGER(0..33554431)															OPTIONAL,
	ie-Extensions				ProtocolExtensionContainer { { GANSS-MeasurementParametersItem-ExtIEs } }	OPTIONAL,
	...
}

GANSS-MeasurementParametersItem-ExtIEs PCAP-PROTOCOL-EXTENSION ::= {
	{ID id-ganssIntegerCodePhaseExt	CRITICALITY	ignore	EXTENSION	GanssIntegerCodePhaseExt PRESENCE	optional},
	...
}

GanssIntegerCodePhaseExt ::= SEQUENCE {
	ganssIntegerCodePhase-ext			INTEGER (64..127),
	ie-Extensions						ProtocolExtensionContainer { { GanssIntegerCodePhaseExt-ExtIEs } } 			OPTIONAL,
	...
}

GanssIntegerCodePhaseExt-ExtIEs PCAP-PROTOCOL-EXTENSION ::= {
	...
}

GANSS-MeasuredResultsList ::=	SEQUENCE (SIZE (1..maxNrOfSets)) OF	GANSS-MeasuredResults

GANSS-MeasuredResults ::= SEQUENCE {
	referenceTime	CHOICE {
		utranReferenceTime		UTRAN-GANSSReferenceTimeUL,
		ganssReferenceTimeOnly	GANSS-ReferenceTimeOnly,
		...
	},
	ganssGenericMeasurementInfo	GANSS-GenericMeasurementInfo,
	ie-Extensions				ProtocolExtensionContainer { { GANSS-MeasuredResults-ExtIEs } } OPTIONAL,
	...
}

GANSS-MeasuredResults-ExtIEs PCAP-PROTOCOL-EXTENSION ::= {
	...
}

GANSS-Navigation-Model ::= SEQUENCE {
	non-broadcastIndication		ENUMERATED{true}		OPTIONAL,
	ganssSatInfoNav				GANSS-Sat-Info-Nav,
	ie-Extensions				ProtocolExtensionContainer { { GANSS-Navigation-Model-ExtIEs } }	OPTIONAL,
	...
}

GANSS-Navigation-Model-ExtIEs PCAP-PROTOCOL-EXTENSION ::= {
	...
}

GANSS-Orbit-Model ::= CHOICE {
	gANSS-keplerianParameters			GANSS-KeplerianParametersOrb,
	...
}

GANSS-Real-Time-Integrity ::= SEQUENCE (SIZE (1..maxGANSSSat)) OF GANSS-RealTimeInformationItem

GANSS-RealTimeInformationItem ::= SEQUENCE {
	bad-ganss-satId						INTEGER(0..63),
	bad-ganss-signalId					BIT STRING(SIZE(8))										OPTIONAL,
	ie-Extensions						ProtocolExtensionContainer { { GANSS-RealTimeInformationItem-ExtIEs } }	OPTIONAL,
	...
}

GANSS-RealTimeInformationItem-ExtIEs PCAP-PROTOCOL-EXTENSION ::= {
	...
}

GANSS-Reference-Location ::= 			SEQUENCE {
	ue-PositionEstimate					UE-PositionEstimate,
	iE-Extensions						ProtocolExtensionContainer { { GANSS-Reference-Location-ExtIEs } }	OPTIONAL,
	...
}

GANSS-Reference-Location-ExtIEs PCAP-PROTOCOL-EXTENSION ::= {
	...
}



GANSS-ReferenceMeasurementInfo ::= SEQUENCE {
	ganssSignalId				GANSS-SignalID														OPTIONAL,
	satelliteInformation		GANSS-SatelliteInformation,
	ie-Extensions				ProtocolExtensionContainer { { GANSS-ReferenceMeasurementInfo-ExtIEs } }	OPTIONAL,
	...
}

GANSS-ReferenceMeasurementInfo-ExtIEs PCAP-PROTOCOL-EXTENSION ::= {
	{ID id-GANSS-Confidence		CRITICALITY ignore	EXTENSION Confidence			PRESENCE optional},
	...
}

GANSS-Reference-Time ::= SEQUENCE {
	ganssDay					INTEGER(0..8191)			OPTIONAL,
	ganssTod					INTEGER(0..86399),
	ganssTodUncertainty			INTEGER(0..127)				OPTIONAL,
	ganssTimeId					GANSSID						OPTIONAL,
	utran-ganssreferenceTime	UTRAN-GANSSReferenceTimeDL	OPTIONAL,
	tutran-ganss-driftRate		TUTRAN-GANSS-DriftRate		OPTIONAL,
	ie-Extensions				ProtocolExtensionContainer { { GANSS-Reference-Time-ExtIEs } }	OPTIONAL,
	...
}

GANSS-Reference-Time-ExtIEs PCAP-PROTOCOL-EXTENSION ::= {
	{ID id-GANSS-Day-Cycle		CRITICALITY		ignore	EXTENSION	GANSS-Day-Cycle		PRESENCE optional},
	...
}

GANSS-Day-Cycle			::=	INTEGER(0..7)

GANSS-ReferenceTimeOnly ::= SEQUENCE {
	gANSS-tod					INTEGER(0..3599999),
	gANSS-timeId				GANSSID			OPTIONAL,
	gANSS-TimeUncertainty		INTEGER(0..127)	OPTIONAL,
	ie-Extensions				ProtocolExtensionContainer { { GANSS-ReferenceTimeOnly-ExtIEs } } OPTIONAL,
	...
}

GANSS-ReferenceTimeOnly-ExtIEs PCAP-PROTOCOL-EXTENSION ::= {
	...
}

GANSS-SatelliteClockModelItem ::= SEQUENCE {
	t-oc								BIT STRING (SIZE(14)),
	a-i2								BIT STRING (SIZE(6)),
	a-i1								BIT STRING (SIZE(21)),
	a-i0								BIT STRING (SIZE(31)),
	t-gd								BIT STRING (SIZE(10))			OPTIONAL,
	sisa								BIT STRING (SIZE(8)),
	model-id							INTEGER(0..3)					OPTIONAL,
	ie-Extensions						ProtocolExtensionContainer { { GANSS-SatelliteClockModelItem-ExtIEs } }	OPTIONAL,
	...
}

GANSS-SatelliteClockModelItem-ExtIEs PCAP-PROTOCOL-EXTENSION ::= {
	...
}

GANSS-SatelliteInformation ::= SEQUENCE(SIZE(1..maxGANSSSat)) OF GANSS-SatelliteInformationItem

GANSS-SatelliteInformationItem ::= SEQUENCE {
	ganssSatId					INTEGER(0..63),
	dopplerZeroOrder			INTEGER(-2048..2047),
	extraDoppler				GANSS-ExtraDoppler				OPTIONAL,
	codePhase					INTEGER(0..1023),
	integerCodePhase			INTEGER(0..127),
	codePhaseSearchWindow		INTEGER(0..31),
	azimuthAndElevation			GANSS-AzimuthAndElevation		OPTIONAL,
	ie-Extensions				ProtocolExtensionContainer { { GANSS-SatelliteInformationItem-ExtIEs } }	OPTIONAL,
	...
}

GANSS-SatelliteInformationItem-ExtIEs PCAP-PROTOCOL-EXTENSION ::= {
	{ID id-GANSS-ExtraDopplerExtension	CRITICALITY ignore	EXTENSION GANSS-ExtraDopplerExtension		PRESENCE optional},
	...
}

GANSS-SatelliteInformationKP ::= SEQUENCE (SIZE (1..maxGANSSSatAlmanac)) OF GANSS-SatelliteInformationKPItem

GANSS-SatelliteInformationKPItem ::= SEQUENCE {
	satId								INTEGER(0..63),
	ganss-e-alm							BIT STRING (SIZE (11)),
	ganss-delta-I-alm					BIT STRING (SIZE (11)),
	ganss-omegadot-alm					BIT STRING (SIZE (11)),
	ganss-svStatusINAV-alm				BIT STRING (SIZE (4)),
	ganss-svStatusFNAV-alm				BIT STRING (SIZE (2))			OPTIONAL,
	ganss-delta-a-sqrt-alm				BIT STRING (SIZE (13)),
	ganss-omegazero-alm					BIT STRING (SIZE (16)),
	ganss-m-zero-alm					BIT STRING (SIZE (16)),
	ganss-omega-alm						BIT STRING (SIZE (16)),
	ganss-af-zero-alm					BIT STRING (SIZE (16)),
	ganss-af-one-alm 					BIT STRING (SIZE (13)),
	ie-Extensions						ProtocolExtensionContainer { { GANSS-SatelliteInformationKPItem-ExtIEs } }	OPTIONAL,
	...
}

GANSS-SatelliteInformationKPItem-ExtIEs PCAP-PROTOCOL-EXTENSION ::= {
	...
}

GANSS-SAT-Info-Almanac-GLOkpList ::= SEQUENCE (SIZE (1.. maxGANSSSatAlmanac)) OF GANSS-SAT-Info-Almanac-GLOkp

GANSS-SAT-Info-Almanac-GLOkp ::= SEQUENCE {
	gloAlmNA				BIT STRING (SIZE(11)),
	gloAlmnA				BIT STRING (SIZE(5)),
	gloAlmHA				BIT STRING (SIZE(5)),
	gloAlmLambdaA			BIT STRING (SIZE(21)),
	gloAlmTlambdaA			BIT STRING (SIZE(21)),
	gloAlmDeltaIA			BIT STRING (SIZE(18)),
	gloAkmDeltaTA			BIT STRING (SIZE(22)),
	gloAlmDeltaTdotA		BIT STRING (SIZE(7)),
	gloAlmEpsilonA			BIT STRING (SIZE(15)),
	gloAlmOmegaA			BIT STRING (SIZE(16)),
	gloAlmTauA				BIT STRING (SIZE(10)),
	gloAlmCA				BIT STRING (SIZE(1)),
	gloAlmMA				BIT STRING (SIZE(2)) 																			OPTIONAL,
	ie-Extensions			ProtocolExtensionContainer { { GANSS-SAT-Info-Almanac-GLOkp-ExtIEs } }	OPTIONAL,
	...
}

GANSS-SAT-Info-Almanac-GLOkp-ExtIEs PCAP-PROTOCOL-EXTENSION ::= {
	...
}

GANSS-SAT-Info-Almanac-MIDIkpList ::= SEQUENCE (SIZE (1.. maxGANSSSatAlmanac)) OF GANSS-SAT-Info-Almanac-MIDIkp

GANSS-SAT-Info-Almanac-MIDIkp ::= SEQUENCE {
	svID					INTEGER(0..63),
	midiAlmE				BIT STRING (SIZE (11)),
	midiAlmDeltaI			BIT STRING (SIZE (11)),
	midiAlmOmegaDot			BIT STRING (SIZE (11)),
	midiAlmSqrtA			BIT STRING (SIZE (17)),
	midiAlmOmega0			BIT STRING (SIZE (16)),
	midiAlmOmega			BIT STRING (SIZE (16)),
	midiAlmMo				BIT STRING (SIZE (16)),
	midiAlmaf0				BIT STRING (SIZE (11)),
	midiAlmaf1				BIT STRING (SIZE (10)),
	midiAlmL1Health			BIT STRING (SIZE (1)),
	midiAlmL2Health			BIT STRING (SIZE (1)),
	midiAlmL5Health			BIT STRING (SIZE (1)),
	ie-Extensions			ProtocolExtensionContainer { { GANSS-SAT-Info-Almanac-MIDIkp-ExtIEs } }	OPTIONAL,
	...
}

GANSS-SAT-Info-Almanac-MIDIkp-ExtIEs PCAP-PROTOCOL-EXTENSION ::= {
	...
}

GANSS-SAT-Info-Almanac-NAVkpList ::= SEQUENCE (SIZE (1.. maxGANSSSatAlmanac)) OF GANSS-SAT-Info-Almanac-NAVkp

GANSS-SAT-Info-Almanac-NAVkp ::= SEQUENCE {
	svID					INTEGER(0..63),
	navAlmE					BIT STRING (SIZE (16)),
	navAlmDeltaI			BIT STRING (SIZE (16)),
	navAlmOMEGADOT			BIT STRING (SIZE (16)),
	navAlmSVHealth			BIT STRING (SIZE (8)),
	navAlmSqrtA				BIT STRING (SIZE (24)),
	navAlmOMEGAo			BIT STRING (SIZE (24)),
	navAlmOmega				BIT STRING (SIZE (24)),
	navAlmMo				BIT STRING (SIZE (24)),
	navAlmaf0				BIT STRING (SIZE (11)),
	navAlmaf1				BIT STRING (SIZE (11)),
	ie-Extensions			ProtocolExtensionContainer { { GANSS-SAT-Info-Almanac-NAVkp-ExtIEs } }	OPTIONAL,
	...
}

GANSS-SAT-Info-Almanac-NAVkp-ExtIEs PCAP-PROTOCOL-EXTENSION ::= {
	...
}

GANSS-SAT-Info-Almanac-REDkpList ::= SEQUENCE (SIZE (1.. maxGANSSSatAlmanac)) OF GANSS-SAT-Info-Almanac-REDkp

GANSS-SAT-Info-Almanac-REDkp ::= SEQUENCE {
	svID					INTEGER(0..63),
	redAlmDeltaA			BIT STRING (SIZE (8)),
	redAlmOmega0			BIT STRING (SIZE (7)),
	redAlmPhi0				BIT STRING (SIZE (7)),
	redAlmL1Health			BIT STRING (SIZE (1)),
	redAlmL2Health			BIT STRING (SIZE (1)),
	redAlmL5Health			BIT STRING (SIZE (1)),
	ie-Extensions			ProtocolExtensionContainer { { GANSS-SAT-Info-Almanac-REDkp-ExtIEs } }	OPTIONAL,
	...
}

GANSS-SAT-Info-Almanac-REDkp-ExtIEs PCAP-PROTOCOL-EXTENSION ::= {
	...
}

GANSS-SAT-Info-Almanac-SBASecefList ::=	SEQUENCE (SIZE (1.. maxGANSSSatAlmanac)) OF GANSS-SAT-Info-Almanac-SBASecef

GANSS-SAT-Info-Almanac-SBASecef ::=	SEQUENCE {
	sbasAlmDataID			BIT STRING (SIZE(2)),
	svID					INTEGER(0..63),
	sbasAlmHealth			BIT STRING (SIZE(8)),
	sbasAlmXg				BIT STRING (SIZE(15)),
	sbasAlmYg				BIT STRING (SIZE(15)),
	sbasAlmZg				BIT STRING (SIZE(9)),
	sbasAlmXgdot			BIT STRING (SIZE(3)),
	sbasAlmYgDot			BIT STRING (SIZE(3)),
	sbasAlmZgDot			BIT STRING (SIZE(4)),
	sbasAlmTo				BIT STRING (SIZE(11)),
	ie-Extensions			ProtocolExtensionContainer { { GANSS-SAT-Info-Almanac-SBASecef-ExtIEs } }	OPTIONAL,
	...
}

GANSS-SAT-Info-Almanac-SBASecef-ExtIEs PCAP-PROTOCOL-EXTENSION ::= {
	...
}

Ganss-Sat-Info-AddNavList ::= SEQUENCE (SIZE (1..maxGANSSSat)) OF SEQUENCE {
	satId						INTEGER (0..63),
	svHealth					BIT STRING (SIZE (6)),
	iod							BIT STRING (SIZE (11)),
	ganssAddClockModels			GANSS-AddClockModels,
	ganssAddOrbitModels			GANSS-AddOrbitModels,
	ie-Extensions				ProtocolExtensionContainer { { Ganss-Sat-Info-AddNavList-ExtIEs } } OPTIONAL,
	...
}

Ganss-Sat-Info-AddNavList-ExtIEs PCAP-PROTOCOL-EXTENSION ::= {
	...
}

GANSS-Sat-Info-Nav ::= SEQUENCE (SIZE(1..maxGANSSSat)) OF SEQUENCE {
	satId						INTEGER(0..63),
	svHealth					BIT STRING (SIZE(9)),
	iod							BIT STRING (SIZE(10)),
	ganssClockModel				GANSS-Clock-Model,
	ganssOrbitModel				GANSS-Orbit-Model,
	ie-Extensions				ProtocolExtensionContainer { { GANSS-Sat-Info-Nav-ExtIEs } } OPTIONAL,
	...
}

GANSS-Sat-Info-Nav-ExtIEs PCAP-PROTOCOL-EXTENSION ::= {
	...
}

GANSS-SignalID ::= SEQUENCE {
	ganssSignalID		INTEGER(0..3,...,4..7),
	ie-Extensions		ProtocolExtensionContainer { { GANSS-SignalID-ExtIEs } } OPTIONAL,
	...
}

GANSS-SignalID-ExtIEs PCAP-PROTOCOL-EXTENSION ::= {
	...
}

GANSS-StatusHealth ::= ENUMERATED {
	udre-scale-1dot0,
	udre-scale-0dot75,
	udre-scale-0dot5,
	udre-scale-0dot3,
	udre-scale-Odot2,
	udre-scale-0dot1,
	no-data,
	invalid-data
}

GANSS-Time-Model ::= SEQUENCE {
	ganss-time-model-refTime			INTEGER(0..37799),
	ganss-t-a0							INTEGER(-2147483648..2147483647),
	ganss-t-a1							INTEGER(-8388608..8388607)									OPTIONAL,
	ganss-t-a2							INTEGER(-64..63)											OPTIONAL,
	gnss-to-id							ENUMERATED{gps,...,galileo,qzss,glonass,bds},
	ganss-wk-number						INTEGER(0..8191)											OPTIONAL,
	ie-Extensions						ProtocolExtensionContainer { { GANSS-Time-Model-ExtIEs } }	OPTIONAL,
	...
}

GANSS-Time-Model-ExtIEs PCAP-PROTOCOL-EXTENSION ::= {
	{ID id-ganss-Delta-T		CRITICALITY		ignore	EXTENSION	GANSS-Delta-T		PRESENCE	optional},
	...
}

GANSS-Delta-T	::=	INTEGER(-128..127)

GANSS-UTRAN-TimeRelationshipUncertainty ::= ENUMERATED {
	gANSS-UTRAN-TRU-50nano,
	gANSS-UTRAN-TRU-500nano,
	gANSS-UTRAN-TRU-1micro,
	gANSS-UTRAN-TRU-10micro,
	gANSS-UTRAN-TRU-1milli,
	gANSS-UTRAN-TRU-10milli,
	gANSS-UTRAN-TRU-100milli,
	gANSS-UTRAN-TRU-unreliable,
...
}

GANSS-UTRAN-TRU ::=	SEQUENCE {
	gANSS-UTRAN-TimeRelationshipUncertainty		GANSS-UTRAN-TimeRelationshipUncertainty,
	ganssId										GANSSID																		OPTIONAL,
	ie-Extensions								ProtocolExtensionContainer { { GANSS-UTRAN-TRU-ExtIEs } }	OPTIONAL,
	...
}

GANSS-UTRAN-TRU-ExtIEs PCAP-PROTOCOL-EXTENSION ::= {
	...
}

GANSS-UTC-Model ::= SEQUENCE {
	a-one-utc							BIT STRING (SIZE (24)),
	a-zero-utc							BIT STRING (SIZE (32)),
	t-ot-utc							BIT STRING (SIZE (8)),
	w-n-t-utc							BIT STRING (SIZE (8)),
	delta-t-ls-utc						BIT STRING (SIZE (8)),
	w-n-lsf-utc							BIT STRING (SIZE (8)),
	dn-utc								BIT STRING (SIZE (8)),
	delta-t-lsf-utc						BIT STRING (SIZE (8)),
	ie-Extensions						ProtocolExtensionContainer { { GANSS-UTC-Model-ExtIEs } }	OPTIONAL,
	...
}

GANSS-UTC-Model-ExtIEs PCAP-PROTOCOL-EXTENSION ::= {
	...
}

TUTRAN-GANSS-DriftRate ::= ENUMERATED {
	uTRAN-GANSSDrift0,		uTRAN-GANSSDrift1,		uTRAN-GANSSDrift2,
	uTRAN-GANSSDrift5,		uTRAN-GANSSDrift10,		uTRAN-GANSSDrift15,
	uTRAN-GANSSDrift25,		uTRAN-GANSSDrift50,		uTRAN-GANSSDrift-1,
	uTRAN-GANSSDrift-2,		uTRAN-GANSSDrift-5,		uTRAN-GANSSDrift-10,
	uTRAN-GANSSDrift-15,	uTRAN-GANSSDrift-25,	uTRAN-GANSSDrift-50,
...
}

GLONASSclockModel ::= SEQUENCE {
	gloTau					BIT STRING (SIZE (22)),
	gloGamma				BIT STRING (SIZE (11)),
	gloDeltaTau				BIT STRING (SIZE (5)) 										OPTIONAL,
	ie-Extensions			ProtocolExtensionContainer { { GLONASSclockModel-ExtIEs } }	OPTIONAL,
	...
}

GLONASSclockModel-ExtIEs PCAP-PROTOCOL-EXTENSION ::= {
	...
}


NAVclockModel ::= SEQUENCE {
	navToc					BIT STRING (SIZE (16)),
	navaf2					BIT STRING (SIZE (8)),
	navaf1					BIT STRING (SIZE (16)),
	navaf0					BIT STRING (SIZE (22)),
	navTgd					BIT STRING (SIZE (8)),
	ie-Extensions			ProtocolExtensionContainer { { NAVclockModel-ExtIEs } }	OPTIONAL,
	...
}

NAVclockModel-ExtIEs PCAP-PROTOCOL-EXTENSION ::= {
	...
}

NavModel-CNAVKeplerianSet ::= SEQUENCE {
	cnavTop					BIT STRING (SIZE (11)),
	cnavURAindex			BIT STRING (SIZE (5)),
	cnavDeltaA				BIT STRING (SIZE (26)),
	cnavAdot				BIT STRING (SIZE (25)),
	cnavDeltaNo				BIT STRING (SIZE (17)),
	cnavDeltaNoDot			BIT STRING (SIZE (23)),
	cnavMo					BIT STRING (SIZE (33)),
	cnavE					BIT STRING (SIZE (33)),
	cnavOmega				BIT STRING (SIZE (33)),
	cnavOMEGA0				BIT STRING (SIZE (33)),
	cnavDeltaOmegaDot		BIT STRING (SIZE (17)),
	cnavIo					BIT STRING (SIZE (33)),
	cnavIoDot				BIT STRING (SIZE (15)),
	cnavCis					BIT STRING (SIZE (16)),
	cnavCic					BIT STRING (SIZE (16)),
	cnavCrs					BIT STRING (SIZE (24)),
	cnavCrc					BIT STRING (SIZE (24)),
	cnavCus					BIT STRING (SIZE (21)),
	cnavCuc					BIT STRING (SIZE (21)),
	ie-Extensions			ProtocolExtensionContainer { { NavModel-CNAVKeplerianSet-ExtIEs } }	OPTIONAL,
	...
}

NavModel-CNAVKeplerianSet-ExtIEs PCAP-PROTOCOL-EXTENSION ::= {
	...
}

NavModel-GLONASSecef ::= SEQUENCE {
	gloEn					BIT STRING (SIZE (5)),
	gloP1					BIT STRING (SIZE (2)),
	gloP2					BIT STRING (SIZE (1)),
	gloM					BIT STRING (SIZE (2))											OPTIONAL,
	gloX					BIT STRING (SIZE (27)),
	gloXdot					BIT STRING (SIZE (24)),
	gloXdotdot				BIT STRING (SIZE (5)),
	gloY					BIT STRING (SIZE (27)),
	gloYdot					BIT STRING (SIZE (24)),
	gloYdotdot				BIT STRING (SIZE (5)),
	gloZ					BIT STRING (SIZE (27)),
	gloZdot					BIT STRING (SIZE (24)),
	gloZdotdot				BIT STRING (SIZE (5)),
	ie-Extensions			ProtocolExtensionContainer { { NavModel-GLONASSecef-ExtIEs } }	OPTIONAL,
	...
}

NavModel-GLONASSecef-ExtIEs PCAP-PROTOCOL-EXTENSION ::= {
	...
}

NavModel-NAVKeplerianSet ::= SEQUENCE {
	navURA					BIT STRING (SIZE (4)),
	navFitFlag				BIT STRING (SIZE (1)),
	navToe					BIT STRING (SIZE (16)),
	navOmega				BIT STRING (SIZE (32)),
	navDeltaN				BIT STRING (SIZE (16)),
	navM0					BIT STRING (SIZE (32)),
	navOmegaADot			BIT STRING (SIZE (24)),
	navE					BIT STRING (SIZE (32)),
	navIDot					BIT STRING (SIZE (14)),
	navAPowerHalf			BIT STRING (SIZE (32)),
	navI0					BIT STRING (SIZE (32)),
	navOmegaA0				BIT STRING (SIZE (32)),
	navCrs					BIT STRING (SIZE (16)),
	navCis					BIT STRING (SIZE (16)),
	navCus					BIT STRING (SIZE (16)),
	navCrc					BIT STRING (SIZE (16)),
	navCic					BIT STRING (SIZE (16)),
	navCuc					BIT STRING (SIZE (16)),
	ie-Extensions			ProtocolExtensionContainer { { NavModel-NAVKeplerianSet-ExtIEs } }	OPTIONAL,
	...
}

NavModel-NAVKeplerianSet-ExtIEs PCAP-PROTOCOL-EXTENSION ::= {
	...
}

NavModel-SBASecef ::= SEQUENCE {
	-- the following IE shall be present if ‘SBASclockModel’ in ‘GANSS-AddClockModels’ is not included in ‘Ganss-Sat-Info-AddNavList’
	sbasTo					BIT STRING (SIZE (13))										OPTIONAL,
	sbasAccuracy			BIT STRING (SIZE (4)),
	sbasXg					BIT STRING (SIZE (30)),
	sbasYg					BIT STRING (SIZE (30)),
	sbasZg					BIT STRING (SIZE (25)),
	sbasXgDot				BIT STRING (SIZE (17)),
	sbasYgDot				BIT STRING (SIZE (17)),
	sbasZgDot				BIT STRING (SIZE (18)),
	sbasXgDotDot			BIT STRING (SIZE (10)),
	sbagYgDotDot			BIT STRING (SIZE (10)),
	sbasZgDotDot			BIT STRING (SIZE (10)),
	ie-Extensions			ProtocolExtensionContainer { { NavModel-SBASecef-ExtIEs } }	OPTIONAL,
	...
}

NavModel-SBASecef-ExtIEs PCAP-PROTOCOL-EXTENSION ::= {
	...
}

NavModel-BDSKeplerianSet ::= SEQUENCE {
	uRAIndex-BDS			BIT STRING (SIZE (4)),
	tOA-BDS					BIT STRING (SIZE (17)),
	a1-2-BDS				BIT STRING (SIZE (32)),
	e-BDS					BIT STRING (SIZE (32)),
	oMG-BDS					BIT STRING (SIZE (32)),
	dLTn-BDS				BIT STRING (SIZE (16)),
	m0-BDS					BIT STRING (SIZE (32)),
	oMG0-BDS				BIT STRING (SIZE (32)),
	oMGdot-BDS				BIT STRING (SIZE (24)),
	i0-BDS					BIT STRING (SIZE (32)),
	iDOT-BDS				BIT STRING (SIZE (14)),
	cuc-BDS					BIT STRING (SIZE (18)),
	cus-BDS					BIT STRING (SIZE (18)),
	crc-BDS					BIT STRING (SIZE (18)),
	crs-BDS					BIT STRING (SIZE (18)),
	cic-BDS					BIT STRING (SIZE (18)),
	cis-BDS					BIT STRING (SIZE (18)),
	aODE-BDS				BIT STRING (SIZE (5)),
	ie-Extensions			ProtocolExtensionContainer { { NavModel-BDSKeplerianSet-ExtIEs } }	OPTIONAL,
	...
}

NavModel-BDSKeplerianSet-ExtIEs PCAP-PROTOCOL-EXTENSION ::= {
	...
}

SBASclockModel ::= SEQUENCE {
	sbasTo					BIT STRING (SIZE (13)),
	sbasAgfo				BIT STRING (SIZE (12)),
	sbasAgf1				BIT STRING (SIZE (8)),
	ie-Extensions			ProtocolExtensionContainer { { SBASclockModel-ExtIEs } }	OPTIONAL,
	...
}

SBASclockModel-ExtIEs PCAP-PROTOCOL-EXTENSION ::= {
	...
}

BDSClockModel ::= SEQUENCE {
	toc-BDS				BIT STRING (SIZE (17) ),
	a0-BDS				BIT STRING (SIZE (24) ),
	a1-BDS				BIT STRING (SIZE (22) ),
	a2-BDS				BIT STRING (SIZE (11) ),
	tGD1-BDS			BIT STRING (SIZE (10) ),
	aODC-BDS			BIT STRING (SIZE (5) ),
	ie-Extensions		ProtocolExtensionContainer { { BDSClockModel-ExtIEs } }	OPTIONAL,
	...
}

BDSClockModel-ExtIEs PCAP-PROTOCOL-EXTENSION ::= {
	...
}

UTCmodelSet1 ::= SEQUENCE {
	utcA0				BIT STRING (SIZE(16)),
	utcA1				BIT STRING (SIZE(13)),
	utcA2				BIT STRING (SIZE(7)),
	utcDeltaTls			BIT STRING (SIZE(8)),
	utcTot				BIT STRING (SIZE(16)),
	utcWNot				BIT STRING (SIZE(13)),
	utcWNlsf			BIT STRING (SIZE(8)),
	utcDN				BIT STRING (SIZE(4)),
	utcDeltaTlsf		BIT STRING (SIZE(8)),
	ie-Extensions		ProtocolExtensionContainer { { UTCmodelSet1-ExtIEs } }	OPTIONAL,
	...
}

UTCmodelSet1-ExtIEs PCAP-PROTOCOL-EXTENSION ::= {
	...
}

UTCmodelSet2 ::= SEQUENCE {
	nA					BIT STRING (SIZE(11)),
	tauC				BIT STRING (SIZE(32)),
	deltaUT1			DeltaUT1												OPTIONAL,
	kp					BIT STRING (SIZE(2)) 									OPTIONAL,
	ie-Extensions		ProtocolExtensionContainer { { UTCmodelSet2-ExtIEs } }	OPTIONAL,
	...
}

UTCmodelSet2-ExtIEs PCAP-PROTOCOL-EXTENSION ::= {
	...
}

UTCmodelSet3 ::= SEQUENCE {
	utcA1wnt			BIT STRING (SIZE(24)),
	utcA0wnt			BIT STRING (SIZE(32)),
	utcTot				BIT STRING (SIZE(8)),
	utcWNt				BIT STRING (SIZE(8)),
	utcDeltaTls			BIT STRING (SIZE(8)),
	utcWNlsf			BIT STRING (SIZE(8)),
	utcDN				BIT STRING (SIZE(8)),
	utcDeltaTlsf		BIT STRING (SIZE(8)),
	utcStandardID		BIT STRING (SIZE(3)),
	ie-Extensions		ProtocolExtensionContainer { { UTCmodelSet3-ExtIEs } }	OPTIONAL,
	...
}

UTCmodelSet3-ExtIEs PCAP-PROTOCOL-EXTENSION ::= {
	...
}

UTCmodelSet4 ::= SEQUENCE {
	utca0-BDS			BIT STRING (SIZE(32)),
	utca1-BDS			BIT STRING (SIZE(24)),
	utcDeltatLS-BDS		BIT STRING (SIZE(8)),
	utcWNt				BIT STRING (SIZE(8)),
	utcDeltaTls			BIT STRING (SIZE(8)),
	utcWNlsf-BDS		BIT STRING (SIZE(8)),
	utcDN-BDS			BIT STRING (SIZE(8)),
	utcDeltaTlsf-BDS	BIT STRING (SIZE(8)),
	ie-Extensions		ProtocolExtensionContainer { { UTCmodelSet4-ExtIEs } }	OPTIONAL,
	...
}

UTCmodelSet4-ExtIEs PCAP-PROTOCOL-EXTENSION ::= {
	...
}

UTRAN-GANSSReferenceTimeDL ::= SEQUENCE {
	utran-GANSSTimingOfCellFrames	INTEGER(0..3999999),
	uC-ID							UC-ID																					OPTIONAL,
	referenceSfn					INTEGER(0..4095),
	ie-Extensions					ProtocolExtensionContainer { { UTRAN-GANSSReferenceTimeDL-ExtIEs } }	OPTIONAL,
	...
}

UTRAN-GANSSReferenceTimeDL-ExtIEs PCAP-PROTOCOL-EXTENSION ::= {
	...
}

UTRAN-GANSSReferenceTimeUL ::= SEQUENCE {
	ue-GANSSTimingOfCellFrames	INTEGER(0..345599999999),
	gANSS-TimeId				GANSSID						OPTIONAL,
	gANSS-TimeUncertainty		INTEGER(0..127)				OPTIONAL,
	uC-ID						UC-ID,
	referenceSfn				INTEGER(0..4095),
	ie-Extensions				ProtocolExtensionContainer { { UTRAN-GANSSReferenceTimeUL-ExtIEs } }	OPTIONAL,
	...
}

UTRAN-GANSSReferenceTimeUL-ExtIEs PCAP-PROTOCOL-EXTENSION ::= {
	...
}


-- **************************************************************
--
-- GPS Almanac and Satellite Health
--
-- **************************************************************


GPS-AlmanacAndSatelliteHealth ::=	SEQUENCE {
	wn-a								BIT STRING (SIZE (8)),
	almanacSatInfoList					AlmanacSatInfoList,
	svGlobalHealth						BIT STRING (SIZE (364)) OPTIONAL,
	iE-Extensions						ProtocolExtensionContainer { { GPS-AlmanacAndSatelliteHealth-ExtIEs } }		OPTIONAL,
	...
}

GPS-AlmanacAndSatelliteHealth-ExtIEs PCAP-PROTOCOL-EXTENSION ::= {
	{ID id-completeAlmanacProvided		CRITICALITY	ignore	EXTENSION	CompleteAlmanacProvided PRESENCE	optional},
	...
}

CompleteAlmanacProvided ::=		BOOLEAN

AlmanacSatInfoList ::=				SEQUENCE (SIZE (1..maxSatAlmanac)) OF
										AlmanacSatInfo

AlmanacSatInfo ::=					SEQUENCE {
	dataID								BIT STRING (SIZE (2)),
	satID								INTEGER (0..63),
	e									BIT STRING (SIZE (16)),
	t-oa								BIT STRING (SIZE (8)),
	deltaI								BIT STRING (SIZE (16)),
	omegaDot							BIT STRING (SIZE (16)),
	satHealth							BIT STRING (SIZE (8)),
	a-Sqrt								BIT STRING (SIZE (24)),
	omega0								BIT STRING (SIZE (24)),
	m0									BIT STRING (SIZE (24)),
	omega								BIT STRING (SIZE (24)),
	af0									BIT STRING (SIZE (11)),
	af1									BIT STRING (SIZE (11)),
	iE-Extensions						ProtocolExtensionContainer { { AlmanacSatInfo-ExtIEs } }	OPTIONAL,
	...
}

AlmanacSatInfo-ExtIEs PCAP-PROTOCOL-EXTENSION ::= {
	...
}


-- **************************************************************
--
-- GPS Clock And Ephemeris Parameters
--
-- **************************************************************

GPS-ClockAndEphemerisParameters ::=	SEQUENCE {
	codeOnL2							BIT STRING (SIZE (2)),
	uraIndex							BIT STRING (SIZE (4)),
	satHealth							BIT STRING (SIZE (6)),
	iodc								BIT STRING (SIZE (10)),
	l2Pflag								BIT STRING (SIZE (1)),
	sf1Revd								SubFrame1Reserved,
	t-GD								BIT STRING (SIZE (8)),
	t-oc								BIT STRING (SIZE (16)),
	af2									BIT STRING (SIZE (8)),
	af1									BIT STRING (SIZE (16)),
	af0									BIT STRING (SIZE (22)),
	c-rs								BIT STRING (SIZE (16)),
	delta-n								BIT STRING (SIZE (16)),
	m0									BIT STRING (SIZE (32)),
	c-uc								BIT STRING (SIZE (16)),
	e									BIT STRING (SIZE (32)),
	c-us								BIT STRING (SIZE (16)),
	a-Sqrt								BIT STRING (SIZE (32)),
	t-oe								BIT STRING (SIZE (16)),
	fitInterval							BIT STRING (SIZE (1)),
	aodo								BIT STRING (SIZE (5)),
	c-ic								BIT STRING (SIZE (16)),
	omega0								BIT STRING (SIZE (32)),
	c-is								BIT STRING (SIZE (16)),
	i0									BIT STRING (SIZE (32)),
	c-rc								BIT STRING (SIZE (16)),
	omega								BIT STRING (SIZE (32)),
	omegaDot							BIT STRING (SIZE (24)),
	iDot								BIT STRING (SIZE (14)),
	iE-Extensions						ProtocolExtensionContainer { { GPS-ClockAndEphemerisParameters-ExtIEs } }		OPTIONAL,
	...
}

GPS-ClockAndEphemerisParameters-ExtIEs PCAP-PROTOCOL-EXTENSION ::= {
	...
}

SubFrame1Reserved ::= 				SEQUENCE {
 	reserved1							BIT STRING (SIZE (23)),
	reserved2							BIT STRING (SIZE (24)),
	reserved3							BIT STRING (SIZE (24)),
	reserved4							BIT STRING (SIZE (16))
}


-- **************************************************************
--
-- GPS Ionospheric Model
--
-- **************************************************************


 GPS-Ionospheric-Model ::=			SEQUENCE {
	alfa0								BIT STRING (SIZE (8)),
	alfa1								BIT STRING (SIZE (8)),
	alfa2								BIT STRING (SIZE (8)),
	alfa3								BIT STRING (SIZE (8)),
	beta0								BIT STRING (SIZE (8)),
	beta1								BIT STRING (SIZE (8)),
	beta2								BIT STRING (SIZE (8)),
	beta3								BIT STRING (SIZE (8)),
	iE-Extensions						ProtocolExtensionContainer { { GPS-Ionospheric-Model-ExtIEs } }		OPTIONAL,
	...
}

GPS-Ionospheric-Model-ExtIEs PCAP-PROTOCOL-EXTENSION ::= {
	...
}

-- **************************************************************
--
-- GPS Measured Results
--
-- **************************************************************

MeasuredResultsList ::=				SEQUENCE (SIZE (1..maxNrOfSets)) OF
	GPS-MeasuredResults

GPS-MeasuredResults ::=				SEQUENCE {
	gps-TOW-1msec						INTEGER (0..604799999),
	gps-MeasurementParamList			GPS-MeasurementParamList,
	iE-Extensions						ProtocolExtensionContainer { { GPS-MeasuredResults-ExtIEs } }	OPTIONAL,
	...
}

GPS-MeasuredResults-ExtIEs PCAP-PROTOCOL-EXTENSION ::= {
	{ID id-UTRAN-GPSReferenceTimeResult	CRITICALITY	ignore	EXTENSION	UTRAN-GPSReferenceTimeResult	PRESENCE	optional} |
	{ID id-GPSReferenceTimeUncertainty	CRITICALITY	ignore	EXTENSION	GPSReferenceTimeUncertainty	PRESENCE	optional},
	...
}

GPS-MeasurementParamList ::=		SEQUENCE (SIZE (1..maxSat)) OF
										GPS-MeasurementParam

GPS-MeasurementParam ::=			SEQUENCE {
	satelliteID							INTEGER (0..63),
	c-N0								INTEGER (0..63),
	doppler								INTEGER (-32768..32768),
	wholeGPS-Chips						INTEGER (0..1022),
	fractionalGPS-Chips					INTEGER (0..1023),
	multipathIndicator					MultipathIndicator,
	pseudorangeRMS-Error				INTEGER (0..63),
	iE-Extensions						ProtocolExtensionContainer { { GPS-MeasurementParam-ExtIEs } }	OPTIONAL,
	...
}

MultipathIndicator ::=				ENUMERATED {
										nm,
										low,
										medium,
										high }

GPS-MeasurementParam-ExtIEs PCAP-PROTOCOL-EXTENSION ::= {
	...
}


-- **************************************************************
--
-- GPS Navigation Model
--
-- **************************************************************


GPS-NavigationModel ::=		SEQUENCE (SIZE (1..maxSat)) OF
										NavigationModelSatInfo

NavigationModelSatInfo ::=			SEQUENCE {
	satID								INTEGER (0..63),
	satelliteStatus						SatelliteStatus,
	gps-clockAndEphemerisParms			GPS-ClockAndEphemerisParameters											OPTIONAL,
	-- This IE is not present if satelliteStatus is es-SN
	iE-Extensions						ProtocolExtensionContainer { { NavigationModelSatInfo-ExtIEs } }	OPTIONAL,
	...
}

NavigationModelSatInfo-ExtIEs PCAP-PROTOCOL-EXTENSION ::= {
	...
}

SatelliteStatus ::=					ENUMERATED {
										ns-NN,
										es-SN,
										es-NN,
										rev2,
										rev }



-- **************************************************************
--
-- GPS Real Time Integrity
--
-- **************************************************************

GPS-RealTimeIntegrity ::= CHOICE {
	badSatellites		BadSatList,
	noBadSatellites		NoBadSatellites,
	...
}

BadSatList ::=						SEQUENCE (SIZE (1..maxSat)) OF
										INTEGER (0..63)

NoBadSatellites ::= NULL

-- **************************************************************
--
-- GPS Reference Location
--
-- **************************************************************

GPS-ReferenceLocation ::= 			SEQUENCE {
	ue-PositionEstimate					UE-PositionEstimate,
	iE-Extensions						ProtocolExtensionContainer { { GPS-ReferenceLocation-ExtIEs } }	OPTIONAL,
	...
}

GPS-ReferenceLocation-ExtIEs PCAP-PROTOCOL-EXTENSION ::= {
	...
}

-- **************************************************************
--
-- GPS Reference Time
--
-- **************************************************************

GPS-ReferenceTime ::=				SEQUENCE {
	gps-Week							INTEGER (0..1023),
	gps-TOW-1msec						INTEGER (0..604799999),
	gps-TOW-AssistList					GPS-TOW-AssistList												OPTIONAL,
	iE-Extensions						ProtocolExtensionContainer { { GPS-ReferenceTime-ExtIEs } }	OPTIONAL,
	...
}

GPS-ReferenceTime-ExtIEs PCAP-PROTOCOL-EXTENSION ::= {
	{ID id-UTRAN-GPSReferenceTime		CRITICALITY	ignore	EXTENSION	UTRAN-GPSReferenceTime			PRESENCE	optional}|
	{ID id-GPS-UTRAN-TRU				CRITICALITY	ignore	EXTENSION	GPS-UTRAN-TRU					PRESENCE	optional}|
	{ID id-UTRAN-GPS-DriftRate			CRITICALITY	ignore	EXTENSION	UTRAN-GPS-DriftRate				PRESENCE	optional}|
	{ID id-GPSReferenceTimeUncertainty	CRITICALITY	ignore	EXTENSION	GPSReferenceTimeUncertainty	PRESENCE	optional}|
	{ID id-GPS-Week-Cycle				CRITICALITY	ignore	EXTENSION	GPS-Week-Cycle					PRESENCE	optional},
	...
}

GPS-Week-Cycle		::=				INTEGER(0..7)

GPS-TOW-AssistList ::=				SEQUENCE (SIZE (1..maxSat)) OF
										GPS-TOW-Assist

GPS-TOW-Assist ::=					SEQUENCE {
	satID								INTEGER (0..63),
	tlm-Message							BIT STRING (SIZE (14)),
	antiSpoof							BOOLEAN,
	alert								BOOLEAN,
	tlm-Reserved						BIT STRING (SIZE (2)),
	iE-Extensions						ProtocolExtensionContainer { { GPS-TOW-Assist-ExtIEs } }	OPTIONAL,
	...
}

GPS-TOW-Assist-ExtIEs PCAP-PROTOCOL-EXTENSION ::= {
	...
}

UTRAN-GPS-DriftRate ::=				ENUMERATED {
									utran-GPSDrift0, utran-GPSDrift1, utran-GPSDrift2,
									utran-GPSDrift5, utran-GPSDrift10, utran-GPSDrift15,
									utran-GPSDrift25, utran-GPSDrift50, utran-GPSDrift-1,
									utran-GPSDrift-2, utran-GPSDrift-5, utran-GPSDrift-10,
									utran-GPSDrift-15, utran-GPSDrift-25, utran-GPSDrift-50,
									...}

-- **************************************************************
--
-- GPS Reference Time Uncertainty
--
-- **************************************************************

GPSReferenceTimeUncertainty ::=	SEQUENCE {
	gps-RefTimeUNC		INTEGER(0..127),
	iE-Extensions		ProtocolExtensionContainer { { GPSReferenceTimeUncertainty-ExtIEs } }	OPTIONAL,
	...
}

GPSReferenceTimeUncertainty-ExtIEs PCAP-PROTOCOL-EXTENSION ::= {
	...
}

-- **************************************************************
--
-- GPS Transmission TOW
--
-- **************************************************************

GPS-Transmission-TOW ::= INTEGER (0..604799)



-- **************************************************************
--
-- GPS UTC Model
--
-- **************************************************************

GPS-UTC-Model ::=					SEQUENCE {
	a1									BIT STRING (SIZE (24)),
	a0									BIT STRING (SIZE (32)),
	t-ot								BIT STRING (SIZE (8)),
	delta-t-LS							BIT STRING (SIZE (8)),
	wn-t								BIT STRING (SIZE (8)),
	wn-lsf								BIT STRING (SIZE (8)),
	dn									BIT STRING (SIZE (8)),
	delta-t-LSF							BIT STRING (SIZE (8)),
	iE-Extensions						ProtocolExtensionContainer { { GPS-UTCmodel-ExtIEs } }	OPTIONAL,
	...
}

GPS-UTCmodel-ExtIEs PCAP-PROTOCOL-EXTENSION ::= {
	...
}


-- **************************************************************
--
-- GPS UTRAN Time Relationship Uncertainty
-- nsec=nanosecond, usec=microsecond, msec=millisecond, sec=second
--
-- **************************************************************

GPS-UTRAN-TRU ::=	ENUMERATED {
						nsec-50,
						nsec-500,
						usec-1,
						usec-10,
						msec-1,
						msec-10,
						msec-100,
						unreliable,
						...}

-- **************************************************************
--
-- Additional GPS Assistance Data Required
--
-- **************************************************************


AdditionalGPSAssistDataRequired ::=		SEQUENCE {
	almanacRequest						BOOLEAN,
	utcModelRequest						BOOLEAN,
	ionosphericModelRequest				BOOLEAN,
	navigationModelRequest				BOOLEAN,
	dgpsCorrectionsRequest				BOOLEAN,
	referenceLocationRequest			BOOLEAN,
	referenceTimeRequest				BOOLEAN,
	aquisitionAssistanceRequest			BOOLEAN,
	realTimeIntegrityRequest			BOOLEAN,
	navModelAddDataRequest				NavModelAdditionalData		OPTIONAL,
	iE-Extensions						ProtocolExtensionContainer { { AdditionalGPSAssistDataRequired-ExtIEs } } OPTIONAL,
	...
}

AdditionalGPSAssistDataRequired-ExtIEs PCAP-PROTOCOL-EXTENSION ::= {
	...
}



-- **************************************************************
--
-- Additional GANSS Assistance Data Required
--
-- **************************************************************

AdditionalGanssAssistDataRequired::= SEQUENCE {
	ganssReferenceTime					BOOLEAN,
	ganssreferenceLocation				BOOLEAN,
	ganssIonosphericModel				BOOLEAN,
	ganssRequestedGenericAssistanceDataList	GanssRequestedGenericAssistanceDataList,
	iE-Extensions						ProtocolExtensionContainer { { AdditionalGanssAssistDataRequired-ExtIEs } } OPTIONAL,
	...
}

AdditionalGanssAssistDataRequired-ExtIEs PCAP-PROTOCOL-EXTENSION ::= {
	{ID id-ganssReq-AddIonosphericModel		CRITICALITY	ignore	EXTENSION	GANSSReq-AddIonosphericModel 	PRESENCE	optional}|
	{ID id-ganssReq-EarthOrientPara			CRITICALITY	ignore	EXTENSION	GANSSReq-EarthOrientPara 		PRESENCE	optional},
	...
}
GANSSReq-AddIonosphericModel ::= SEQUENCE {
	ganss-add-iono-mode-req		BIT STRING (SIZE(2)),
	iE-Extensions				ProtocolExtensionContainer { { GANSSReq-AddIonosphericModel-ExtIEs } }	OPTIONAL,
	...}

GANSSReq-AddIonosphericModel-ExtIEs PCAP-PROTOCOL-EXTENSION ::= {
	...
}

GANSSReq-EarthOrientPara ::= BOOLEAN

GanssRequestedGenericAssistanceDataList ::= SEQUENCE (SIZE (1..maxGANSS)) OF
										GanssReqGenericData

GanssReqGenericData ::=				SEQUENCE {
	ganssId								GANSSID																OPTIONAL,
	ganssRealTimeIntegrity				BOOLEAN																OPTIONAL,
	ganssDifferentialCorrection			DGANSS-Sig-Id-Req													OPTIONAL,
	ganssAlmanac						BOOLEAN																OPTIONAL,
	ganssNavigationModel				BOOLEAN																OPTIONAL,
	ganssTimeModelGnssGnss				BIT STRING (SIZE (9))												OPTIONAL,
	ganssReferenceMeasurementInfo		BOOLEAN																OPTIONAL,
	ganssDataBits						GanssDataBits														OPTIONAL,
	ganssUTCModel						BOOLEAN																OPTIONAL,
	ganssNavigationModelAdditionalData	NavigationModelGANSS												OPTIONAL,
	iE-Extensions						ProtocolExtensionContainer { { GanssReqGenericData-ExtIEs } }	OPTIONAL,
	...}

GanssReqGenericData-ExtIEs PCAP-PROTOCOL-EXTENSION ::= {
	{ID id-ganssAddNavigationModel-req		CRITICALITY ignore	EXTENSION GANSS-AddNavigationModel-Req		PRESENCE optional}|
	{ID id-ganssAddUTCModel-req				CRITICALITY ignore	EXTENSION GANSS-AddUTCModel-Req				PRESENCE optional}|
	{ID id-ganssAuxInfo-req					CRITICALITY ignore	EXTENSION GANSS-AuxInfo-req					PRESENCE optional}|
	{ID id-GANSS-SBAS-ID					CRITICALITY ignore	EXTENSION GANSS-SBAS-ID						PRESENCE optional}|
	{ID id-GANSS-AddADchoices				CRITICALITY ignore	EXTENSION GANSS-AddADchoices				PRESENCE optional}|
	{ID id-BDSIonosphericGridModel			CRITICALITY ignore	EXTENSION BDSIonosphericGridModel			PRESENCE optional}|
	{ID id-DBDSCorrection					CRITICALITY ignore	EXTENSION DBDSCorrection					PRESENCE optional},
	...
}

BDSIonosphericGridModel ::= BOOLEAN

DBDSCorrection ::=	SEQUENCE {
	dGANSSSignalBDS				BIT STRING (SIZE (8)),
	iE-Extensions				ProtocolExtensionContainer { { DBDSCorrection-ExtIEs } }	OPTIONAL,
	...
}

DBDSCorrection-ExtIEs PCAP-PROTOCOL-EXTENSION ::= {
	...
}

GANSS-AddNavigationModel-Req ::= BOOLEAN

GANSS-AddUTCModel-Req ::= BOOLEAN

GANSS-AuxInfo-req ::= BOOLEAN

GANSS-AddADchoices ::= SEQUENCE {
	orbitModelID			INTEGER (0..7)													OPTIONAL,
	clockModelID			INTEGER (0..7)													OPTIONAL,
	utcModelID				INTEGER (0..7)													OPTIONAL,
	almanacModelID			INTEGER (0..7)													OPTIONAL,
	iE-Extensions			ProtocolExtensionContainer { { GANSS-AddADchoices-ExtIEs } }	OPTIONAL,
	...}

GANSS-AddADchoices-ExtIEs PCAP-PROTOCOL-EXTENSION ::= {
	...
}

DGANSS-Sig-Id-Req ::=	BIT STRING (SIZE (8))

GanssDataBits ::=				SEQUENCE {
	ganssTod					INTEGER (0..86399),
	dataBitAssistancelist		ReqDataBitAssistanceList,
	iE-Extensions				ProtocolExtensionContainer { { GanssDataBits-ExtIEs } }	OPTIONAL,
	...
}

GanssDataBits-ExtIEs PCAP-PROTOCOL-EXTENSION ::= {
	...
}


ReqDataBitAssistanceList ::=	SEQUENCE {
	ganssSignalID				BIT STRING (SIZE (8)),
	ganssDataBitInterval		INTEGER(0..15),
	ganssSatelliteInfo			SEQUENCE (SIZE (1..maxGANSSSat)) OF INTEGER(0..63) 						OPTIONAL,
	iE-Extensions				ProtocolExtensionContainer { { ReqDataBitAssistanceList-ExtIEs } }	OPTIONAL,
	...
}


ReqDataBitAssistanceList-ExtIEs PCAP-PROTOCOL-EXTENSION ::= {
	...
}


-- **************************************************************
--
-- Information Exchange ID
--
-- **************************************************************

InformationExchangeID ::= INTEGER (0..1048575)


-- **************************************************************
--
-- Information Report Characteristics
--
-- **************************************************************

InformationReportCharacteristics ::= SEQUENCE {
	type					InformationReportCharacteristicsType,
	periodicity				InformationReportPeriodicity		OPTIONAL,
	-- present if type indicates periodic
	...
}

InformationReportCharacteristicsType ::= ENUMERATED {
	onDemand,
	periodic,
	onModification,
	...
}


InformationReportPeriodicity ::= CHOICE {
	min				INTEGER (1..60, ...),
-- Unit min, Step 1min
	hour			INTEGER (1..24, ...),
-- Unit hour, Step 1hour
	...
}

-- **************************************************************
--
-- Information Type
--
-- **************************************************************


InformationType ::= CHOICE {
	implicitInformation			MethodType,
	explicitInformation			ExplicitInformationList,
	...
}


ExplicitInformationList ::= SEQUENCE (SIZE (1..maxNrOfExpInfo)) OF ExplicitInformation

ExplicitInformation ::= CHOICE {
	almanacAndSatelliteHealth			AlmanacAndSatelliteHealth,
	utcModel							UtcModel,
	ionosphericModel					IonosphericModel,
	navigationModel						NavigationModel,
	dgpsCorrections						DgpsCorrections,
	referenceTime						ReferenceTime,
	acquisitionAssistance				AcquisitionAssistance,
	realTimeIntegrity					RealTimeIntegrity,
	almanacAndSatelliteHealthSIB		AlmanacAndSatelliteHealthSIB-InfoType,
	... ,
	referenceLocation					ReferenceLocation,
	ganss-Common-DataReq				GANSSCommonDataReq,
	ganss-Generic-DataList				GANSSGenericDataList

}

DganssCorrectionsReq ::= SEQUENCE {
	transmissionGanssTimeIndicator	TransmissionGanssTimeIndicator									OPTIONAL,
	dganss-sig-id-req				DGANSS-Sig-Id-Req,
	iE-Extensions					ProtocolExtensionContainer { { DganssCorrectionsReq-ExtIEs} } OPTIONAL,
	...
}

DganssCorrectionsReq-ExtIEs PCAP-PROTOCOL-EXTENSION ::= {
	...
}

Ganss-almanacAndSatelliteHealthReq ::= SEQUENCE {
	transmissionGanssTimeIndicator	TransmissionGanssTimeIndicator	OPTIONAL,
	iE-Extensions				ProtocolExtensionContainer { { Ganss-almanacAndSatelliteHealthReq-ExtIEs} } OPTIONAL,
	...
}

Ganss-almanacAndSatelliteHealthReq-ExtIEs PCAP-PROTOCOL-EXTENSION ::= {
	...
}

GANSSCommonDataReq ::= SEQUENCE{
	ganss-ReferenceTime				ENUMERATED {requested, not-requested}	OPTIONAL,
	ganss-IonosphericModel 			ENUMERATED {requested, not-requested}	OPTIONAL,
	ganss-ReferenceLocation 		ENUMERATED {requested, not-requested}	OPTIONAL,
	ie-Extensions					ProtocolExtensionContainer { { GANSSCommonDataReq-ExtIEs } }	OPTIONAL,
	...
}

GANSSCommonDataReq-ExtIEs PCAP-PROTOCOL-EXTENSION ::= {
	{ID id-GANSS-AddIonoModelReq		CRITICALITY	ignore	EXTENSION	GANSS-AddIonoModelReq			PRESENCE	optional} |
	{ID id-GANSS-EarthOrientParaReq		CRITICALITY	ignore	EXTENSION	GANSS-EarthOrientParaReq		PRESENCE	optional} ,
	...
}

GANSS-AddIonoModelReq ::= SEQUENCE {
	dataID			BIT STRING (SIZE(2)),
	iE-Extensions	ProtocolExtensionContainer { { GANSS-AddIonoModelReq-ExtIEs} } 	OPTIONAL,
	...
}

GANSS-AddIonoModelReq-ExtIEs PCAP-PROTOCOL-EXTENSION ::= {
	...
}

GANSS-EarthOrientParaReq ::= SEQUENCE {
	eopReq			ENUMERATED {requested, not-requested},
	iE-Extensions	ProtocolExtensionContainer { { GANSS-EarthOrientParaReq-ExtIEs} } 	OPTIONAL,
	...
}

GANSS-EarthOrientParaReq-ExtIEs PCAP-PROTOCOL-EXTENSION ::= {
	...
}

GANSSGenericDataList ::= SEQUENCE (SIZE(1..maxGANSS)) OF GANSSGenericDataReq

GANSSGenericDataReq ::= SEQUENCE {
	ganssID								GANSSID									OPTIONAL,
	ganss-realTimeIntegrity				Ganss-realTimeIntegrityReq				OPTIONAL,
	ganss-dataBitAssistance				GanssDataBits							OPTIONAL,
	dganssCorrections					DganssCorrectionsReq					OPTIONAL,
	ganss-almanacAndSatelliteHealth		Ganss-almanacAndSatelliteHealthReq		OPTIONAL,
	ganss-referenceMeasurementInfo		Ganss-referenceMeasurementInfoReq		OPTIONAL,
	ganss-utcModel						Ganss-utcModelReq						OPTIONAL,
	ganss-TimeModel-Gnss-Gnss			Ganss-TimeModel-Gnss-Gnss				OPTIONAL,
	navigationModel						NavigationModelGANSS					OPTIONAL,
	...,
	ganss-AddNavModelsReq				AddNavigationModelsGANSS				OPTIONAL,
	ganss-AddUtcModelsReq				GANSS-AddUtcModelsReq					OPTIONAL,
	ganss-AuxInfoReq					GANSS-AuxInfoReq						OPTIONAL,
	-- the following IE shall be present if GANSSID is ‘0’ (SBAS)
	ganss-SBAS-ID						GANSS-SBAS-ID							OPTIONAL,
	dBDS-Corrections					DBDS-Corrections						OPTIONAL,
	bDS-Ionospheric-Grid-Model-Request	BDS-Ionospheric-Grid-Model-Request		OPTIONAL
}

AddNavigationModelsGANSS ::= SEQUENCE {
	ganssWeek					INTEGER(0..4095),
	ganssTOE					INTEGER(0..167),
	t-toe-limit					INTEGER(0..10),
	addSatRelatedDataListGANSS	AddSatelliteRelatedDataListGANSS,
	iE-Extensions				ProtocolExtensionContainer { { AddNavigationModelsGANSS-ExtIEs } } 	OPTIONAL,
	...
}

AddNavigationModelsGANSS-ExtIEs PCAP-PROTOCOL-EXTENSION ::= {
	...
}

AddSatelliteRelatedDataListGANSS ::= SEQUENCE (SIZE (0..maxGANSSSat)) OF AddSatelliteRelatedDataGANSS

AddSatelliteRelatedDataGANSS ::= SEQUENCE {
	satID						INTEGER (0..63),
	iod							BIT STRING (SIZE(10)),
	iE-Extensions				ProtocolExtensionContainer { { AddSatelliteRelatedDataGANSS-ExtIEs } } OPTIONAL,
	...
}

AddSatelliteRelatedDataGANSS-ExtIEs PCAP-PROTOCOL-EXTENSION ::= {
	...
}

BDS-Ionospheric-Grid-Model-Request ::= ENUMERATED 	{
	requested,
	...
}

DBDS-Corrections ::= SEQUENCE {
	transmissionGanssTimeIndicator	TransmissionGanssTimeIndicator	OPTIONAL,
	dGANSS-Signal					BIT STRING( SIZE (8)),
	iE-Extensions					ProtocolExtensionContainer { { DBDS-Corrections-ExtIEs } } 	OPTIONAL,
	...
}

DBDS-Corrections-ExtIEs PCAP-PROTOCOL-EXTENSION ::= {
	...
}

GANSS-AddUtcModelsReq ::= SEQUENCE {
	transmissionGanssTimeIndicator	TransmissionGanssTimeIndicator										OPTIONAL,
	iE-Extensions					ProtocolExtensionContainer { { GANSS-AddUtcModelsReq-ExtIEs} }	OPTIONAL,
	...
}

GANSS-AddUtcModelsReq-ExtIEs PCAP-PROTOCOL-EXTENSION ::= {
	...
}

GANSS-AuxInfoReq ::= SEQUENCE {
	transmissionGanssTimeIndicator	TransmissionGanssTimeIndicator										OPTIONAL,
	iE-Extensions					ProtocolExtensionContainer { { GANSS-AuxInfoReq-ExtIEs} }			OPTIONAL,
	...
}

GANSS-AuxInfoReq-ExtIEs PCAP-PROTOCOL-EXTENSION ::= {
	...
}


GANSS-SBAS-ID ::= ENUMERATED 	{
								waas,
								egnos,
								msas,
								gagan,
								...
								}


Ganss-utcModelReq ::= SEQUENCE {
	transmissionGanssTimeIndicator	TransmissionGanssTimeIndicator	OPTIONAL,
	iE-Extensions				ProtocolExtensionContainer { { Ganss-utcModelReq-ExtIEs} } OPTIONAL,
	...
}

Ganss-utcModelReq-ExtIEs PCAP-PROTOCOL-EXTENSION ::= {
	...
}

Ganss-realTimeIntegrityReq ::= SEQUENCE {
	transmissionGanssTimeIndicator	TransmissionGanssTimeIndicator	OPTIONAL,
	iE-Extensions				ProtocolExtensionContainer { { Ganss-realTimeIntegrityReq-ExtIEs} } OPTIONAL,
	...
}

Ganss-realTimeIntegrityReq-ExtIEs PCAP-PROTOCOL-EXTENSION ::= {
	...
}


Ganss-referenceMeasurementInfoReq ::= SEQUENCE {
	transmissionGanssTimeIndicator	TransmissionGanssTimeIndicator	OPTIONAL,
	iE-Extensions				ProtocolExtensionContainer { { Ganss-referenceMeasurementInfoReq-ExtIEs} } OPTIONAL,
	...
}

Ganss-referenceMeasurementInfoReq-ExtIEs PCAP-PROTOCOL-EXTENSION ::= {
	...
}



Ganss-TimeModel-Gnss-Gnss ::= SEQUENCE{
	ganssTimeModelGnssGnssExt		BIT STRING (SIZE(9)),
	transmissionGanssTimeIndicator	TransmissionGanssTimeIndicator	OPTIONAL,
	iE-Extensions					ProtocolExtensionContainer { { Ganss-TimeModel-Gnss-Gnss-ExtIEs} } OPTIONAL,
	...
}

Ganss-TimeModel-Gnss-Gnss-ExtIEs PCAP-PROTOCOL-EXTENSION ::= {
	...
}

TransmissionGanssTimeIndicator ::= ENUMERATED {
	requested,
	not-Requested
}

AlmanacAndSatelliteHealth ::= NULL

UtcModel ::= SEQUENCE {
	transmissionTOWIndicator	TransmissionTOWIndicator,
	iE-Extensions				ProtocolExtensionContainer { { UtcModel-ExtIEs } } OPTIONAL,
	...
}

UtcModel-ExtIEs PCAP-PROTOCOL-EXTENSION ::= {
	...
}

IonosphericModel ::= SEQUENCE {
	transmissionTOWIndicator	TransmissionTOWIndicator,
	iE-Extensions				ProtocolExtensionContainer { { IonosphericModel-ExtIEs } } OPTIONAL,
	...
}

IonosphericModel-ExtIEs PCAP-PROTOCOL-EXTENSION ::= {
	...
}

NavigationModel ::= SEQUENCE {
	transmissionTOWIndicator		TransmissionTOWIndicator,
	navModelAdditionalData				NavModelAdditionalData			OPTIONAL,
	iE-Extensions				ProtocolExtensionContainer { { NavigationModel-ExtIEs } }	OPTIONAL,
	...
}

NavigationModel-ExtIEs PCAP-PROTOCOL-EXTENSION ::= {
	...
}


NavModelAdditionalData ::= SEQUENCE {
	gps-Week					INTEGER (0..1023),
	gps-TOE						INTEGER (0..167),
	t-TOE-limit					INTEGER (0..10),
	satRelatedDataList			SatelliteRelatedDataList,
	iE-Extensions				ProtocolExtensionContainer { { NavModelAdditionalData-ExtIEs } } OPTIONAL,
	...
}

NavModelAdditionalData-ExtIEs PCAP-PROTOCOL-EXTENSION ::= {
	...
}

SatelliteRelatedDataList ::= SEQUENCE (SIZE (0..maxSat)) OF SatelliteRelatedData

SatelliteRelatedData ::= SEQUENCE {
	satID						INTEGER (0..63),
	iode						INTEGER (0..255),
	iE-Extensions				ProtocolExtensionContainer { { SatelliteRelatedData-ExtIEs } } OPTIONAL,
	...
}

SatelliteRelatedData-ExtIEs PCAP-PROTOCOL-EXTENSION ::= {
	...
}

NavigationModelGANSS ::= SEQUENCE {
	ganssWeek					INTEGER(0..4095),
	ganssTOE					INTEGER(0..167),
	t-toe-limit					INTEGER(0..10),
	satRelatedDataListGANSS		SatelliteRelatedDataListGANSS,
	iE-Extensions				ProtocolExtensionContainer { { NavigationModelGANSS-ExtIEs } } OPTIONAL,
	...
}

NavigationModelGANSS-ExtIEs PCAP-PROTOCOL-EXTENSION ::= {
	...
}

SatelliteRelatedDataListGANSS ::= SEQUENCE (SIZE (0..maxGANSSSat)) OF SatelliteRelatedDataGANSS

SatelliteRelatedDataGANSS ::= SEQUENCE {
	satID						INTEGER (0..63),
	iod							BIT STRING (SIZE(10)),
	iE-Extensions				ProtocolExtensionContainer { { SatelliteRelatedDataGANSS-ExtIEs } } OPTIONAL,
	...
}

SatelliteRelatedDataGANSS-ExtIEs PCAP-PROTOCOL-EXTENSION ::= {
	...
}

DgpsCorrections ::= NULL

ReferenceTime ::= NULL

AcquisitionAssistance ::= NULL

RealTimeIntegrity ::= NULL

AlmanacAndSatelliteHealthSIB-InfoType ::= SEQUENCE {
	transmissionTOWIndicator		TransmissionTOWIndicator,
	iE-Extensions				ProtocolExtensionContainer { { AlmanacAndSatelliteHealthSIB-InfoType-ExtIEs } } OPTIONAL,
	...
}

AlmanacAndSatelliteHealthSIB-InfoType-ExtIEs PCAP-PROTOCOL-EXTENSION ::= {
	...
}

ReferenceLocation ::= NULL

TransmissionTOWIndicator ::= ENUMERATED {
	requested,
	not-Requested
}

-- **************************************************************
--
-- Message Structure
--
-- **************************************************************

MessageStructure ::= SEQUENCE (SIZE (1..maxNrOfLevels)) OF
	SEQUENCE {
		iE-ID					ProtocolIE-ID,
		repetitionNumber		MessageStructureRepetition									OPTIONAL,
		iE-Extensions			ProtocolExtensionContainer { {MessageStructure-ExtIEs} }	OPTIONAL,
		...
	}

MessageStructureRepetition ::= INTEGER (1..256)

MessageStructure-ExtIEs PCAP-PROTOCOL-EXTENSION ::= {
	...
}

-- **************************************************************
--
-- Measurement Instructions Used
--
-- **************************************************************

MeasInstructionsUsed ::= SEQUENCE {
	measurementValidity			MeasurementValidity,
	iE-Extensions				ProtocolExtensionContainer { { MeasInstructionsUsed-ExtIEs } }	OPTIONAL,
	...
}

MeasInstructionsUsed-ExtIEs PCAP-PROTOCOL-EXTENSION ::= {
	...
}


-- **************************************************************
--
-- Measurement Validity
--
-- **************************************************************

MeasurementValidity ::=	SEQUENCE {
	ue-State			ENUMERATED { cell-DCH, all-States-Except-Cell-DCH, all-States, ... },
	iE-Extensions		ProtocolExtensionContainer { { MeasurementValidity-ExtIEs } }	OPTIONAL,
	...
}
MeasurementValidity-ExtIEs PCAP-PROTOCOL-EXTENSION ::= {
	...
}

-- **************************************************************
--
-- Method Type
--
-- **************************************************************

MethodType ::= ENUMERATED {
	ue-assisted,
	ue-based
}


-- **************************************************************
--
-- OTDOA Measurement Group
--
-- **************************************************************

OTDOA-MeasurementGroup ::=			SEQUENCE {
	otdoa-ReferenceCellInfo				OTDOA-ReferenceCellInfo,
	otdoa-NeighbourCellInfoList			OTDOA-NeighbourCellInfoList,
	otdoa-MeasuredResultsSets			OTDOA-MeasuredResultsSets,
	iE-Extensions						ProtocolExtensionContainer { { OTDOA-MeasurementGroup-ExtIEs } }		OPTIONAL,
	...
}

OTDOA-MeasurementGroup-ExtIEs PCAP-PROTOCOL-EXTENSION ::= {
	...
}

OTDOA-ReferenceCellInfo ::=				SEQUENCE {
	uC-ID								UC-ID,
	uTRANAccessPointPositionAltitude	UTRANAccessPointPositionAltitude,
	tUTRANGPSMeasurementValueInfo		TUTRANGPSMeasurementValueInfo												OPTIONAL,
	iE-Extensions						ProtocolExtensionContainer { { OTDOA-ReferenceCellInfo-ExtIEs } }		OPTIONAL,
	...
}

OTDOA-ReferenceCellInfo-ExtIEs PCAP-PROTOCOL-EXTENSION ::= {
	{ ID id-TUTRANGANSSMeasurementValueInfo		CRITICALITY ignore	EXTENSION TUTRANGANSSMeasurementValueInfo				PRESENCE optional }|
	{ ID id-additionalMeasurementInforLCR		CRITICALITY ignore	EXTENSION AdditionalMeasurementInforLCR				PRESENCE optional },
	 -- 1.28Mcps TDD only
	...
}

OTDOA-ReferenceCellInfoSAS-centric ::=			SEQUENCE {
	uC-ID								UC-ID,
	iE-Extensions						ProtocolExtensionContainer { { OTDOA-ReferenceCellInfoSAS-centric-ExtIEs } }		OPTIONAL,
	...
}

OTDOA-ReferenceCellInfoSAS-centric-ExtIEs PCAP-PROTOCOL-EXTENSION ::= {
	...
}

OTDOA-NeighbourCellInfoList ::=			SEQUENCE (SIZE (1..maxNrOfMeasNCell)) OF
	OTDOA-NeighbourCellInfo

OTDOA-NeighbourCellInfo ::=				SEQUENCE {
	uC-ID								UC-ID,
	uTRANAccessPointPositionAltitude	UTRANAccessPointPositionAltitude,
	relativeTimingDifferenceInfo		RelativeTimingDifferenceInfo,
	iE-Extensions						ProtocolExtensionContainer { { OTDOA-NeighbourCellInfo-ExtIEs } }		OPTIONAL,
	...
}

OTDOA-NeighbourCellInfo-ExtIEs PCAP-PROTOCOL-EXTENSION ::= {
	...
}

OTDOA-MeasuredResultsSets ::=			SEQUENCE (SIZE (1..maxNrOfMeasurements)) OF
	OTDOA-MeasuredResultsInfoList

OTDOA-MeasuredResultsInfoList ::=		SEQUENCE (SIZE (1..maxNrOfMeasNCell)) OF
	OTDOA-MeasuredResultsInfo

OTDOA-MeasuredResultsInfo ::=			SEQUENCE {
	uC-ID								UC-ID,
	ue-SFNSFNTimeDifferenceType2Info	UE-SFNSFNTimeDifferenceType2Info,
	iE-Extensions						ProtocolExtensionContainer { { OTDOA-MeasuredResultsInfo-ExtIEs } }		OPTIONAL,
	...
}

OTDOA-MeasuredResultsInfo-ExtIEs PCAP-PROTOCOL-EXTENSION ::= {
	{ID id-OTDOA-AddMeasuredResultsInfo	CRITICALITY	ignore	EXTENSION	OTDOA-AddMeasuredResultsInfo	PRESENCE	optional},
	...
}

OTDOA-AddMeasuredResultsInfo ::= SEQUENCE {
	primaryCPICH-Info		PrimaryScramblingCode,
	iE-Extensions			ProtocolExtensionContainer { { OTDOA-AddMeasuredResultsInfo-ExtIEs } }		OPTIONAL,
	...
}

OTDOA-AddMeasuredResultsInfo-ExtIEs PCAP-PROTOCOL-EXTENSION ::= {
	...
}

UE-SFNSFNTimeDifferenceType2Info ::=	SEQUENCE {
	ue-SFNSFNTimeDifferenceType2		INTEGER (0..40961),
	ue-PositioningMeasQuality			UE-PositioningMeasQuality,
	measurementDelay					INTEGER (0..65535),
	iE-Extensions						ProtocolExtensionContainer { { UE-SFNSFNTimeDifferenceInfo-ExtIEs } }		OPTIONAL,
	...
}

UE-SFNSFNTimeDifferenceInfo-ExtIEs PCAP-PROTOCOL-EXTENSION ::= {
	...
}

UC-ID ::=								SEQUENCE {
	rNC-ID								INTEGER (0..4095),
	c-ID								INTEGER (0..65535),
	iE-Extensions						ProtocolExtensionContainer { { UC-ID-ExtIEs } }		OPTIONAL,
	...
}

UC-ID-ExtIEs PCAP-PROTOCOL-EXTENSION ::= {
	{ ID id-Extended-RNC-ID		CRITICALITY reject		EXTENSION	Extended-RNC-ID	PRESENCE	optional},
	...
}

Extended-RNC-ID ::= INTEGER (4096..65535)


RelativeTimingDifferenceInfo ::= CHOICE {
	sFNSFNMeasurementValueInfo			SFNSFNMeasurementValueInfo,
	tUTRANGPSMeasurementValueInfo		TUTRANGPSMeasurementValueInfo,
	...,
	tUTRANGANSSMeasurementValueInfo		TUTRANGANSSMeasurementValueInfo
}

SFNSFNMeasurementValueInfo ::= SEQUENCE {
	sFNSFNValue							SFNSFNValue,
	sFNSFNQuality						SFNSFNQuality																OPTIONAL,
	sFNSFNDriftRate						SFNSFNDriftRate,
	sFNSFNDriftRateQuality				SFNSFNDriftRateQuality														OPTIONAL,
	iE-Extensions						ProtocolExtensionContainer { { SFNSFNMeasurementValueInfo-ExtIEs } }	OPTIONAL,
	...
}

SFNSFNMeasurementValueInfo-ExtIEs PCAP-PROTOCOL-EXTENSION ::= {
	...
}

SFNSFNValue ::= 						INTEGER (0..614399)

SFNSFNQuality ::= 						INTEGER (0..255)
-- Unit chip, Step 1/16 chip, Range 0.. 255/16 chip

SFNSFNDriftRate ::= 					INTEGER (-100..100)
-- Unit chip/s, Step 1/256 chip/s, Range -100/256..+100/256 chip/s

SFNSFNDriftRateQuality ::= 				INTEGER (0..100)
-- Unit chip/s, Step 1/256 chip/s, Range 0..100/256 chip/s

TUTRANGPSMeasurementValueInfo ::= SEQUENCE {
	sFN									SFN,
	tUTRANGPS							TUTRANGPS,
	tUTRANGPSQuality					TUTRANGPSQuality																OPTIONAL,
	tUTRANGPSDriftRate					TUTRANGPSDriftRate,
	tUTRANGPSDriftRateQuality			TUTRANGPSDriftRateQuality														OPTIONAL,
	iE-Extensions						ProtocolExtensionContainer { { TUTRANGPSMeasurementValueInfo-ExtIEs } }	OPTIONAL,
	...
}

TUTRANGPSMeasurementValueInfo-ExtIEs PCAP-PROTOCOL-EXTENSION ::= {
	...
}

SFN ::=									INTEGER (0..4095)

TUTRANGPS ::= 							SEQUENCE {
	ms-part 							INTEGER (0..16383),
	ls-part								INTEGER (0..4294967295)
}

TUTRANGPSQuality ::= 					INTEGER (0..255)
-- Unit chip, Step 1/16 chip, Range 0.. 255/16 chip

TUTRANGPSDriftRate ::= 					INTEGER (-50..50)
-- Unit chip/s, Step 1/256 chip/s, Range -50/256..+50/256 chip/s

TUTRANGPSDriftRateQuality ::= 			INTEGER (0..50)
-- Unit chip/s, Step 1/256 chip/s, Range 0..50/256 chip/s

TUTRANGANSSMeasurementValueInfo ::= SEQUENCE {
	ganssID								GANSSID					OPTIONAL,
	sFN									SFN,
	tUTRANGANSS							TUTRANGANSS,
	tUTRANGANSSQuality					INTEGER(0..255)			OPTIONAL,
	tUTRANGANSSDriftRate				INTEGER(-50..50),
	tUTRANGANSSDriftRateQuality			INTEGER(0..50)			OPTIONAL,
	iE-Extensions						ProtocolExtensionContainer { { TUTRANGANSSMeasurementValueInfo-ExtIEs } }	OPTIONAL,
	...
}

TUTRANGANSSMeasurementValueInfo-ExtIEs PCAP-PROTOCOL-EXTENSION ::= {
	...
}

TUTRANGANSS ::= 							SEQUENCE {
	ms-part 							INTEGER (0..16383),
	ls-part								INTEGER (0..4294967295)
}

AdditionalMeasurementInforLCR ::=	SEQUENCE {
	timingAdvanceLCR-R7			TimingAdvanceLCR-R7,
	rxTimingDeviationLCR 		RxTimingDeviationLCR,
	angleOfArrivalLCR			AngleOfArrivalLCR			OPTIONAL,
	iE-Extensions				ProtocolExtensionContainer { { AdditionalMeasurementInforLCR-ExtIEs } } OPTIONAL,
	...
}

AdditionalMeasurementInforLCR-ExtIEs PCAP-PROTOCOL-EXTENSION ::= {
	...
}

TimingAdvanceLCR-R7 ::=		INTEGER (0..8191)

-- **************************************************************
--
-- Periodic Position Calculation Info
--
-- **************************************************************

PeriodicPosCalcInfo ::= SEQUENCE {
	referenceNumber				INTEGER (0..32767, ...),
	amountOutstandingRequests	INTEGER (1..8639999, ...),
	reportingInterval			INTEGER (1..8639999, ...),
	iE-Extensions				ProtocolExtensionContainer { { PeriodicPosCalcInfo-ExtIEs } }	OPTIONAL,
	...
}

PeriodicPosCalcInfo-ExtIEs PCAP-PROTOCOL-EXTENSION ::= {
	...
}


-- **************************************************************
--
-- Periodic Location Info
--
-- **************************************************************

PeriodicLocationInfo ::= SEQUENCE {
	reportingAmount				INTEGER (1..8639999, ...),
	reportingInterval			INTEGER (1..8639999, ...),
	iE-Extensions				ProtocolExtensionContainer { { PeriodicLocationInfo-ExtIEs } }	OPTIONAL,
	...
}

PeriodicLocationInfo-ExtIEs PCAP-PROTOCOL-EXTENSION ::= {
	...
}

-- **************************************************************
--
-- Periodic Termination Cause
--
-- **************************************************************

PeriodicTerminationCause ::= ENUMERATED {
					rrc-state-transition,
					cancelled-by-srnc,
					cancelled-by-sas,
					undefined,
					...
					}

-- **************************************************************
--
-- Positioning Method
--
-- **************************************************************

PositioningMethod ::= SEQUENCE {
	additionalMethodType			AdditionalMethodType,
	selectedPositionMethod			SelectedPositionMethod,
	iE-Extensions					ProtocolExtensionContainer { { PositioningMethod-ExtIEs } }	OPTIONAL,
	...
}



PositioningMethod-ExtIEs PCAP-PROTOCOL-EXTENSION ::= {
-- The following IE shall be present if the Selected Position Method IE value is set to "GNSS" or “OTDOA or GNSS”
	{ ID id-GNSS-PositioningMethod			CRITICALITY ignore	EXTENSION GNSS-PositioningMethod		PRESENCE conditional}|
-- This IE shall be present if the Selected Position Method IE value is set to “GPS and AddPos” or “OTDOA or GPS and AddPos”
	{ ID id-Additional-PositioningMethod	CRITICALITY ignore	EXTENSION Additional-PositioningMethod	PRESENCE conditional},
	...
}

GNSS-PositioningMethod ::= BIT STRING (SIZE(9))

Additional-PositioningMethod ::= BIT STRING (SIZE(8))

SelectedPositionMethod ::= ENUMERATED {
	oTDOA,
	gPS,
	oTDOA-or-GPS,
	cell-id,
	uTDOA,
	...,
	gNSS,
	oTDOA-or-GNSS,
	gPS-and-AddPos,
	oTDOA-or-GPS-and-AddPos
}

-- **************************************************************
--
-- Positioning Priority
--
-- **************************************************************
PositioningPriority ::= ENUMERATED {
	high-priority,
	normal-priority,
	...
}

-- **************************************************************
--
-- RRC State Change
--
-- **************************************************************

RRCstateChange ::=	SEQUENCE {
	new-ue-State		ENUMERATED { cell-DCH, cell-FACH, cell-PCH, ura-PCH, ... },
	iE-Extensions		ProtocolExtensionContainer { { RRCstateChange-ExtIEs } }	OPTIONAL,
	...
}

RRCstateChange-ExtIEs PCAP-PROTOCOL-EXTENSION ::= {
	...
}

-- **************************************************************
--
-- Requested Data Value
--
-- **************************************************************

RequestedDataValue ::= SEQUENCE {
	gpsAlmanacAndSatelliteHealth		GPS-AlmanacAndSatelliteHealth									OPTIONAL,
	gps-UTC-Model						GPS-UTC-Model													OPTIONAL,
	gps-Ionospheric-Model				GPS-Ionospheric-Model											OPTIONAL,
	gps-NavigationModel					GPS-NavigationModel												OPTIONAL,
	dgpsCorrections						DGPSCorrections													OPTIONAL,
	referenceTime						GPS-ReferenceTime												OPTIONAL,
	gps-AcquisitionAssistance			GPS-AcquisitionAssistance										OPTIONAL,
	gps-RealTime-Integrity				GPS-RealTimeIntegrity											OPTIONAL,
	almanacAndSatelliteHealthSIB 		AlmanacAndSatelliteHealthSIB									OPTIONAL,
	gps-Transmission-TOW				GPS-Transmission-TOW											OPTIONAL,
	iE-Extensions						ProtocolExtensionContainer { { RequestedDataValue-ExtIEs} }	OPTIONAL,
	...
}

--at least one of the above IEs shall be present in the requested data value

RequestedDataValue-ExtIEs PCAP-PROTOCOL-EXTENSION ::= {
	{ ID id-GPS-ReferenceLocation			CRITICALITY ignore	EXTENSION GPS-ReferenceLocation					PRESENCE optional }|
	{ ID id-GANSS-CommonAssistanceData		CRITICALITY ignore	EXTENSION GANSS-CommonAssistanceData			PRESENCE optional }|
	{ ID id-GANSS-GenericAssistanceDataList	CRITICALITY ignore	EXTENSION GANSS-GenericAssistanceDataList	PRESENCE optional },
	...
}

-- **************************************************************
--
-- Requested Data Value Information
--
-- **************************************************************

RequestedDataValueInformation ::= CHOICE {
	informationAvailable		InformationAvailable,
	informationNotAvailable		InformationNotAvailable
}

InformationAvailable::= SEQUENCE {
	requestedDataValue		RequestedDataValue,
	iE-Extensions			ProtocolExtensionContainer { { InformationAvailable-ExtIEs} }	OPTIONAL,
	...
}

InformationAvailable-ExtIEs PCAP-PROTOCOL-EXTENSION ::= {
	...
}

InformationNotAvailable ::= NULL

-- **************************************************************
--
-- Request Type
--
-- **************************************************************
RequestType ::= SEQUENCE {
	event			RequestTypeEvent,
	reportArea		RequestTypeReportArea,
	horizontalaccuracyCode	RequestTypeAccuracyCode		OPTIONAL,
	iE-Extensions	ProtocolExtensionContainer { { RequestType-ExtIEs} }	OPTIONAL,
	...
}

RequestType-ExtIEs PCAP-PROTOCOL-EXTENSION ::= {
	...
}

RequestTypeEvent ::= ENUMERATED {
	stop-change-of-service-area,
	direct,
	change-of-service-area,
	stop-direct,
	...,
	periodic,
	stop-periodic
}

RequestTypeReportArea ::= ENUMERATED {
	service-area,
	geographical-area,
	...
}

RequestTypeAccuracyCode ::= INTEGER (0..127)

-- **************************************************************
--
-- Response Time
--
-- **************************************************************
ResponseTime ::= ENUMERATED {
	low-delay,
	delay-tolerant,
	...
}

-- **************************************************************
--
-- Horizontal Accuracy Code
--
-- **************************************************************

HorizontalAccuracyCode			::= INTEGER (0..127)

-- **************************************************************
--
-- UE Positioning Capability
--
-- **************************************************************
UE-PositioningCapability ::= SEQUENCE {
	standAloneLocationMethodsSupported	BOOLEAN,
	ueBasedOTDOASupported				BOOLEAN,
	networkAssistedGPSSupport			NetworkAssistedGPSSuport,
	supportGPSTimingOfCellFrame			BOOLEAN,
	supportForIPDL						BOOLEAN,
	supportForRxTxTimeDiff				BOOLEAN,
	supportForUEAGPSinCellPCH			BOOLEAN,
	supportForSFNSFNTimeDiff			BOOLEAN,
	iE-Extensions						ProtocolExtensionContainer { {UE-PositioningCapability-ExtIEs} }	OPTIONAL,
	...
}

UE-PositioningCapability-ExtIEs PCAP-PROTOCOL-EXTENSION ::= {
	{ ID id-NetworkAssistedGANSSSuport		CRITICALITY ignore	EXTENSION NetworkAssistedGANSSSupport		PRESENCE optional}|
	{ ID id-AddPosSupport					CRITICALITY ignore	EXTENSION AddPosSupport						PRESENCE optional},
	...
}

NetworkAssistedGANSSSupport ::= SEQUENCE (SIZE (1..maxGANSS)) OF SEQUENCE {
	ganssID								GANSSID											OPTIONAL,
	ganssMode							ENUMERATED {
												networkBased,
												ue-Based,
												both,
												none
										},
	ganssSignalID						GANSS-SignalID									OPTIONAL,
	supportGANSSTimingOfCellFrame		BOOLEAN,
	supportGANSSCarrierPhaseMeasurement	BOOLEAN,
	iE-Extensions	ProtocolExtensionContainer { { NetworkAssistedGANSSSuport-ExtIEs} }	OPTIONAL,
	...
}

AddPosSupport ::= SEQUENCE (SIZE (1..maxAddPos)) OF AddPosSupport-Element

AddPosSupport-Element ::= SEQUENCE {
	addPosID			ENUMERATED {
							barometricPressure,
							wLAN,
							bluetooth,
							mBS,
							...
						},
	addPosMode			ENUMERATED {
							standalone,
							ue-assisted,
							both,
							...
						},
	...
}

NetworkAssistedGANSSSuport-ExtIEs PCAP-PROTOCOL-EXTENSION ::= {
	-- the following IE shall be present if ‘GANSSID’ in ‘NetworkAssistedGANSSSupport’ is ‘0’ (SBAS)
	{ ID id-GANSS-SBAS-IDs					CRITICALITY ignore	EXTENSION GANSS-SBAS-IDs						PRESENCE optional }|
	{ ID id-GANSS-Signal-IDs				CRITICALITY ignore	EXTENSION GANSS-Signal-IDs						PRESENCE optional }|
	{ ID id-supportGANSSNonNativeADchoices	CRITICALITY ignore	EXTENSION SupportGANSSNonNativeADchoices	PRESENCE optional },
	...
}

NetworkAssistedGPSSuport ::= ENUMERATED {
	network-based,
	ue-based,
	both,
	none,
	...
}

GANSS-SBAS-IDs ::= SEQUENCE {
	ganss-sbas-ids		BIT STRING (SIZE(8)),
	iE-Extensions		ProtocolExtensionContainer { { GANSS-SBAS-IDs-ExtIEs} }	OPTIONAL,
	...
}

GANSS-SBAS-IDs-ExtIEs PCAP-PROTOCOL-EXTENSION ::= {
	...
}


GANSS-Signal-IDs ::= SEQUENCE {
	ganss-signal-ids	BIT STRING (SIZE(8)),
	iE-Extensions		ProtocolExtensionContainer { { GANSS-Signal-IDs-ExtIEs} }	OPTIONAL,
	...
}

GANSS-Signal-IDs-ExtIEs PCAP-PROTOCOL-EXTENSION ::= {
	...
}


SupportGANSSNonNativeADchoices ::= BOOLEAN

-- **************************************************************
--
-- UTDOA Positioning (Position Activation Request Message)
--
-- **************************************************************

UTDOAPositioning ::= SEQUENCE {
	utdoa-BitCount			UTDOA-BitCount,
	utdoa-timeInterval		UTDOA-TimeInterval,
	iE-Extensions		ProtocolExtensionContainer { { UTDOAPositioning-ExtIEs } } OPTIONAL,
	...
}


UTDOAPositioning-ExtIEs PCAP-PROTOCOL-EXTENSION ::= {
	...
}


UTDOA-BitCount ::= INTEGER (0..5000)

UTDOA-TimeInterval	::= INTEGER (0..3000)

EnvironmentCharacterisation	::=	ENUMERATED { heavyMultipathandNLOSconditions,
				noOrLightMultipathAndUsuallyLOSconditions,
				notDefinedOrMixedEnvironment,
				...
				}


-- **************************************************************
--
-- GPS and GANSS Positioning (Position Activation Request Message)
--
-- **************************************************************
GPSPositioning ::= SEQUENCE {
	gpsPositioningInstructions		GPSPositioningInstructions,
	requestedDataValue 				RequestedDataValue			OPTIONAL,
	iE-Extensions					ProtocolExtensionContainer { { GPSPositioning-ExtIEs } } OPTIONAL,
	...
}

GPSPositioning-ExtIEs PCAP-PROTOCOL-EXTENSION ::= {
	...
}

GPSPositioningInstructions ::= SEQUENCE {
	horizontalAccuracyCode				HorizontalAccuracyCode															OPTIONAL,
	verticalAccuracyCode				VerticalAccuracyCode															OPTIONAL,
	gpsTimingOfCellWanted				BOOLEAN,
	additionalAssistanceDataRequest		BOOLEAN,
	iE-Extensions						ProtocolExtensionContainer 	{ { GPSPositioningInstructions-ExtIEs } } 	OPTIONAL,
	...
}

GPSPositioningInstructions-ExtIEs PCAP-PROTOCOL-EXTENSION ::= {
	{ID id-MeasurementValidity		CRITICALITY		ignore		EXTENSION		MeasurementValidity		PRESENCE optional},
	...
}

GANSSPositioning ::= SEQUENCE {
	ganssPositioningInstructions	GANSS-PositioningInstructions,
	requestedDataValue				RequestedDataValue				OPTIONAL,
	iE-Extensions					ProtocolExtensionContainer { { GANSSPositioning-ExtIEs } } OPTIONAL,
	...
}

GANSSPositioning-ExtIEs PCAP-PROTOCOL-EXTENSION ::= {
	...
}

GANSS-PositioningInstructions ::= SEQUENCE {
	horizontalAccuracyCode				HorizontalAccuracyCode															OPTIONAL,
	verticalAccuracyCode				VerticalAccuracyCode															OPTIONAL,
	ganssTimingOfCellWanted				BIT STRING (SIZE (8)),
	additionalAssistanceDataRequest		BIT STRING (SIZE (8)),
	measurementValidity					MeasurementValidity																OPTIONAL,
	iE-Extensions						ProtocolExtensionContainer { { GANSS-PositioningInstructions-ExtIEs } } 	OPTIONAL,
	...
}

GANSS-PositioningInstructions-ExtIEs PCAP-PROTOCOL-EXTENSION ::= {
	{ID id-GANSScarrierPhaseRequested	CRITICALITY	ignore	EXTENSION	GANSScarrierPhaseRequested	PRESENCE optional}|
	{ID id-GANSSMultiFreqMeasRequested	CRITICALITY	ignore	EXTENSION	GANSSMultiFreqMeasRequested	PRESENCE optional},
	...
}

GANSScarrierPhaseRequested ::= BIT STRING (SIZE (8))

GANSSMultiFreqMeasRequested ::= BIT STRING (SIZE (8))


-- **************************************************************
--
-- OTDOA Assistance Data
--
-- **************************************************************
OTDOAAssistanceData ::= SEQUENCE {
	uE-Positioning-OTDOA-AssistanceData			UE-Positioning-OTDOA-AssistanceData,
	iE-Extensions								ProtocolExtensionContainer { { OTDOAAssistanceData-ExtIEs } } OPTIONAL,
	...

}
OTDOAAssistanceData-ExtIEs PCAP-PROTOCOL-EXTENSION ::= {
	...
}

-- ************************************
--
-- UE Positioning OTDOA Assistance Data
--
-- ************************************

UE-Positioning-OTDOA-AssistanceData ::=		SEQUENCE {
	ue-positioning-OTDOA-ReferenceCellInfo			UE-Positioning-OTDOA-ReferenceCellInfo				OPTIONAL,
	ue-positioning-OTDOA-NeighbourCellList			UE-Positioning-OTDOA-NeighbourCellList				OPTIONAL,
	iE-Extensions									ProtocolExtensionContainer { { UE-Positioning-OTDOAAssistanceData-ExtIEs } } OPTIONAL,
	...
}

UE-Positioning-OTDOAAssistanceData-ExtIEs PCAP-PROTOCOL-EXTENSION ::= {
	...
}

UE-Positioning-OTDOA-ReferenceCellInfo ::=	SEQUENCE {
	sfn									SFN									OPTIONAL,
	modeSpecificInfo CHOICE {
		fdd										SEQUENCE {
			primaryCPICH-Info					PrimaryScramblingCode,
			...
		},
		tdd										SEQUENCE{
			cellParameterID						CellParameterID,
		--- coding is FFS
			...
		},
		...
	},
	frequencyInfo						FrequencyInfo						OPTIONAL,
	positioningMode CHOICE {
		ueBased									SEQUENCE {
			cellPosition								ReferenceCellPosition	OPTIONAL,
			-- actual value roundTripTime = (IE value * 0.0625) + 876
			roundTripTime						INTEGER (0..32766)				OPTIONAL,
			...
		},
		ueAssisted								SEQUENCE {
			...
		},
		...
	},
	ue-positioning-IPDL-Paremeters				UE-Positioning-IPDL-Parameters	OPTIONAL,
	iE-Extensions						ProtocolExtensionContainer { { UE-Positioning-OTDOAReferenceCellInfo-ExtIEs } } OPTIONAL,
	...
}

UE-Positioning-OTDOAReferenceCellInfo-ExtIEs PCAP-PROTOCOL-EXTENSION ::= {
	{ ID id-ExtendedRoundTripTime	CRITICALITY ignore	EXTENSION ExtendedRoundTripTime			PRESENCE optional }| -- FDD only
	{ ID id-timingAdvanceLCR-R7		CRITICALITY ignore	EXTENSION TimingAdvanceLCR-R7			PRESENCE optional }| -- 1.28Mcps TDD only
	{ ID id-rxTimingDeviationLCR	CRITICALITY ignore	EXTENSION RxTimingDeviationLCR			PRESENCE optional }| -- 1.28Mcps TDD only
	{ ID id-angleOfArrivalLCR		CRITICALITY ignore	EXTENSION AngleOfArrivalLCR				PRESENCE optional }, -- 1.28Mcps TDD only
	...
}

ReferenceCellPosition ::=			CHOICE {
	ellipsoidPoint						GeographicalCoordinates,
	ellipsoidPointWithAltitude			GA-PointWithAltitude,
	...
}



UE-Positioning-IPDL-Parameters ::=			SEQUENCE {
	modeSpecificInfo					CHOICE {
		fdd									SEQUENCE {
			ip-Spacing							IP-Spacing,
			ip-Length							IP-Length,
			ip-Offset							INTEGER (0..9),
			seed								INTEGER (0..63),
			...
		},
		tdd									SEQUENCE {
			-- coding is FFS
			...
		},
		...
	},
	burstModeParameters					BurstModeParameters				OPTIONAL,
	iE-Extensions						ProtocolExtensionContainer { { UE-Positioning-IPDL-Parameters-ExtIEs } } OPTIONAL,
	...
}

UE-Positioning-IPDL-Parameters-ExtIEs PCAP-PROTOCOL-EXTENSION ::= {
	...
}

IP-Spacing ::=						ENUMERATED {
										e5, e7, e10, e15, e20,
										e30, e40, e50, ... }

IP-Length ::=						ENUMERATED {
										ipl5, ipl10, ... }

BurstModeParameters ::=				SEQUENCE {
	burstStart							INTEGER (0..15),
	burstLength							INTEGER (10..25),
	burstFreq							INTEGER (1..16),
	iE-Extensions						ProtocolExtensionContainer { { BurstModeParameters-ExtIEs } } OPTIONAL,

	...
}

BurstModeParameters-ExtIEs PCAP-PROTOCOL-EXTENSION ::= {
	...
}



UE-Positioning-OTDOA-NeighbourCellList ::= SEQUENCE (SIZE (1..maxCellMeas)) OF
											UE-Positioning-OTDOA-NeighbourCellInfo


UE-Positioning-OTDOA-NeighbourCellInfo ::= SEQUENCE {
	modeSpecificInfo	CHOICE	{
		fdd								SEQUENCE {
			primaryCPICH-Info					PrimaryScramblingCode,
			...
		},
		tdd								SEQUENCE{
			cellParameterID						CellParameterID,
			-- coding is FFS
			...
		},
		...
	},
	frequencyInfo						FrequencyInfo						OPTIONAL,
	ue-positioning-IPDL-Paremeters		UE-Positioning-IPDL-Parameters		OPTIONAL,
	sfn-SFN-RelTimeDifference			SFN-SFN-RelTimeDifference1,
	sfn-Offset-Validity					SFN-Offset-Validity					OPTIONAL,
	sfn-SFN-Drift						SFN-SFN-Drift						OPTIONAL,
	searchWindowSize					OTDOA-SearchWindowSize,
	positioningMode		CHOICE {
		ueBased									SEQUENCE {
			relativeNorth						INTEGER (-20000..20000)				OPTIONAL,
			relativeEast						INTEGER (-20000..20000)				OPTIONAL,
			relativeAltitude					INTEGER (-4000..4000)				OPTIONAL,
			fineSFN-SFN							FineSFNSFN							OPTIONAL,
			-- actual value roundTripTime = (IE value * 0.0625) + 876
			roundTripTime						INTEGER (0.. 32766)					OPTIONAL,
			...
		},
		ueAssisted								SEQUENCE {
			...
		},
		...
	},
	iE-Extensions						ProtocolExtensionContainer { { UE-Positioning-OTDOANeighbourCellInfo-ExtIEs } } OPTIONAL,
	...
}

UE-Positioning-OTDOANeighbourCellInfo-ExtIEs PCAP-PROTOCOL-EXTENSION ::= {
	{ ID id-ExtendedRoundTripTime	CRITICALITY ignore	EXTENSION ExtendedRoundTripTime			PRESENCE optional }, -- FDD only
	...
}


SFN-SFN-RelTimeDifference1 ::=		SEQUENCE {
	sfn-Offset							INTEGER (0 .. 4095),
	sfn-sfn-Reltimedifference			INTEGER (0.. 38399),
	iE-Extensions						ProtocolExtensionContainer { { SFN-SFN-RelTimeDifference1-ExtIEs } } OPTIONAL,
	...
}

SFN-SFN-RelTimeDifference1-ExtIEs PCAP-PROTOCOL-EXTENSION ::= {
	...
}

SFN-Offset-Validity ::=			ENUMERATED { false }

OTDOA-SearchWindowSize ::=			ENUMERATED {
										c20, c40, c80, c160, c320,
										c640, c1280, moreThan1280, ... }

SFN-SFN-Drift ::= 					ENUMERATED {
										sfnsfndrift0, sfnsfndrift1, sfnsfndrift2,
										sfnsfndrift3, sfnsfndrift4, sfnsfndrift5,
										sfnsfndrift8, sfnsfndrift10, sfnsfndrift15,
										sfnsfndrift25, sfnsfndrift35, sfnsfndrift50,
										sfnsfndrift65, sfnsfndrift80, sfnsfndrift100,
										sfnsfndrift-1, sfnsfndrift-2, sfnsfndrift-3,
										sfnsfndrift-4, sfnsfndrift-5, sfnsfndrift-8,
										sfnsfndrift-10, sfnsfndrift-15, sfnsfndrift-25,
										sfnsfndrift-35, sfnsfndrift-50, sfnsfndrift-65,
										sfnsfndrift-80, sfnsfndrift-100, ...}


FineSFNSFN		::=	INTEGER (0..15)
-- Range 0..0.9375 step size 0.0625


-- **************************************************************
--
-- Vertical Accuracy Code
--
-- **************************************************************

VerticalAccuracyCode			::= INTEGER (0..127)


-- **************************************************************
--
-- UTDOA Group
--
-- **************************************************************

UTDOA-Group ::=			SEQUENCE {
	uC-ID								UC-ID,
	frequencyInfo						FrequencyInfo,
	uTDOA-ChannelSettings				UTDOA-RRCState,
	iE-Extensions						ProtocolExtensionContainer { { UTDOA-Group-ExtIEs } }		OPTIONAL,
	...
}

UTDOA-Group-ExtIEs PCAP-PROTOCOL-EXTENSION ::= {
	...
}


FrequencyInfo ::=					SEQUENCE {
	modeSpecificInfo					CHOICE {
		fdd									FrequencyInfoFDD,
		tdd									FrequencyInfoTDD,
		...
		},
	iE-Extensions				ProtocolExtensionContainer { { FrequencyInfo-ExtIEs } }		OPTIONAL,
	...
}

FrequencyInfo-ExtIEs PCAP-PROTOCOL-EXTENSION ::= {
	...
}

FrequencyInfoFDD ::=				SEQUENCE {
	uarfcn-UL							UARFCN				OPTIONAL,
	uarfcn-DL							UARFCN,
	iE-Extensions				ProtocolExtensionContainer { { FrequencyInfoFDD-ExtIEs } }		OPTIONAL,
	...
}

FrequencyInfoFDD-ExtIEs PCAP-PROTOCOL-EXTENSION ::= {
	...
}

FrequencyInfoTDD ::=				SEQUENCE {

	uarfcn								UARFCN,
	iE-Extensions		ProtocolExtensionContainer { {FrequencyInfoTDD-ExtIEs} }				OPTIONAL,
	...
}

FrequencyInfoTDD-ExtIEs PCAP-PROTOCOL-EXTENSION ::= {
	...
}


UTDOA-RRCState ::=	CHOICE {
	uTDOA-CELLDCH	UTDOA-CELLDCH,
	uTDOA-CELLFACH	UTDOA-CELLFACH,
	...
}

-- ***********************************
--
-- UTDOA Cell DCH Information
--
-- ***********************************
UTDOA-CELLDCH ::=		SEQUENCE {
	uL-DPCHInfo									UL-DPCHInfo,
	compressedModeAssistanceData				Compressed-Mode-Assistance-Data		OPTIONAL,
	dCH-Information								DCH-Information		OPTIONAL,
	e-DPCH-Information							E-DPCH-Information	OPTIONAL,
	iE-Extensions								ProtocolExtensionContainer { { UTDOA-CELLDCH-ExtIEs} } OPTIONAL,
	...
}

UTDOA-CELLDCH-ExtIEs		PCAP-PROTOCOL-EXTENSION ::= {
	...
}

UL-DPCHInfo ::=						CHOICE {
		fdd									SEQUENCE {
			scramblingCodeType					ScramblingCodeType,
			scramblingCode						UL-ScramblingCode,
			tfci-Existence						BOOLEAN,
			numberOfFBI-Bits					NumberOfFBI-Bits,
			iE-Extensions						ProtocolExtensionContainer { { UL-DPCHInfoFDD-ExtIEs} } OPTIONAL,
			...

		},
		tdd									SEQUENCE {
			cellParameterID						CellParameterID,
			tFCI-Coding							TFCI-Coding,
			punctureLimit						PuncturingLimit,
			repetitionPeriod					RepetitionPeriod,
			repetitionLength					RepetitionLength,
			tdd-DPCHOffset						TDD-DPCHOffset,
			uL-Timeslot-Information				UL-Timeslot-Information,
			frameOffset							FrameOffset,
			specialBurstScheduling				SpecialBurstScheduling,
			iE-Extensions						ProtocolExtensionContainer { { UL-DPCHInfoTDD-ExtIEs} } OPTIONAL,
			...
		},
		...

	}

UL-DPCHInfoFDD-ExtIEs		PCAP-PROTOCOL-EXTENSION ::= {
	...
}

UL-DPCHInfoTDD-ExtIEs		PCAP-PROTOCOL-EXTENSION ::= {
	...
}

Compressed-Mode-Assistance-Data ::=		SEQUENCE {
			dl-information					DL-InformationFDD,
			ul-information					UL-InformationFDD,
			iE-Extensions					ProtocolExtensionContainer { { Compressed-Mode-Assistance-DataFDD-ExtIEs} } OPTIONAL,
			...

}

Compressed-Mode-Assistance-DataFDD-ExtIEs		PCAP-PROTOCOL-EXTENSION ::= {
	...
}

DL-InformationFDD ::=				SEQUENCE {
			primaryScramblingCode			PrimaryScramblingCode,
			chipOffset						ChipOffset,
			frameOffset						FrameOffset,
			iE-Extensions					ProtocolExtensionContainer { { DL-InformationFDD-ExtIEs} } OPTIONAL,
			...
		}

DL-InformationFDD-ExtIEs		PCAP-PROTOCOL-EXTENSION ::= {
	...
}

UL-InformationFDD ::=				SEQUENCE {
			transmissionGapPatternSequenceInfo			Transmission-Gap-Pattern-Sequence-Information,
			activePatternSequenceInfo					Active-Pattern-Sequence-Information,
			cFN											CFN,
			iE-Extensions								ProtocolExtensionContainer { { UL-InformationFDD-ExtIEs} } OPTIONAL,
			...
	}

UL-InformationFDD-ExtIEs		PCAP-PROTOCOL-EXTENSION ::= {
	...
}

Transmission-Gap-Pattern-Sequence-Information ::= SEQUENCE (SIZE (1..maxTGPS)) OF
	SEQUENCE {
		tGPSID								TGPSID,
		tGSN								TGSN,
		tGL1								GapLength,
		tGL2								GapLength	OPTIONAL,
		tGD									TGD,
		tGPL1								GapDuration,
		uplink-Compressed-Mode-Method		Uplink-Compressed-Mode-Method,
		iE-Extensions						ProtocolExtensionContainer { {Transmission-Gap-Pattern-Sequence-Information-ExtIEs} } OPTIONAL,
		...
	}

Transmission-Gap-Pattern-Sequence-Information-ExtIEs PCAP-PROTOCOL-EXTENSION ::= {
	...
}

TGD					::= INTEGER (0|15..269)
-- 0 = Undefined, only one transmission gap in the transmission gap pattern sequence

TGPRC 				::= INTEGER (0..511)
-- 0 = infinity

TGPSID				::= INTEGER (1.. maxTGPS)


TGSN				::= INTEGER (0..14)


Uplink-Compressed-Mode-Method 	::= ENUMERATED {
	sFdiv2,
	higher-layer-scheduling,
	...
}

GapDuration				::= INTEGER (1..144,...)
-- Unit frame

GapLength				::= INTEGER (1..14)
-- Unit slot

Active-Pattern-Sequence-Information ::= SEQUENCE {
	cMConfigurationChangeCFN					CFN,
	transmission-Gap-Pattern-Sequence-Status	Transmission-Gap-Pattern-Sequence-Status-List	OPTIONAL,
	iE-Extensions								ProtocolExtensionContainer { {Active-Pattern-Sequence-Information-ExtIEs} } OPTIONAL,
	...
}

Active-Pattern-Sequence-Information-ExtIEs PCAP-PROTOCOL-EXTENSION ::= {
	...
}

Transmission-Gap-Pattern-Sequence-Status-List ::= SEQUENCE (SIZE (1..maxTGPS)) OF
	SEQUENCE {
		tGPSID				TGPSID,
		tGPRC				TGPRC,
		tGCFN				CFN,
		iE-Extensions		ProtocolExtensionContainer { { Transmission-Gap-Pattern-Sequence-Status-List-ExtIEs } } OPTIONAL,
		...
}

Transmission-Gap-Pattern-Sequence-Status-List-ExtIEs PCAP-PROTOCOL-EXTENSION ::= {
	...
}

DCH-Information ::=		SEQUENCE {
	tFCS										TFCS,
	trChInfo									TrChInfoList,
	iE-Extensions								ProtocolExtensionContainer { { DCH-Information-ExtIEs} } OPTIONAL,
	...
}

DCH-Information-ExtIEs		PCAP-PROTOCOL-EXTENSION ::= {
	...
}


TrChInfoList ::= SEQUENCE (SIZE(1..maxTrCH)) OF
		UL-TrCHInfo

UL-TrCHInfo ::=		SEQUENCE {
	uL-TrCHtype							UL-TrCHType,
	tfs									TransportFormatSet,
	iE-Extensions						ProtocolExtensionContainer { { UL-TrCHInfo-ExtIEs} } OPTIONAL,
	...
}

UL-TrCHInfo-ExtIEs		PCAP-PROTOCOL-EXTENSION ::= {
	...
}

UL-TrCHType ::=		ENUMERATED {dch, usch, ...}


E-DPCH-Information ::= SEQUENCE {
	maxSet-E-DPDCHs								Max-Set-E-DPDCHs,
	ul-PunctureLimit							PuncturingLimit,
	e-TFCS-Information							E-TFCS-Information,
	e-TTI										E-TTI,
	e-DPCCH-PO									E-DPCCH-PO			OPTIONAL,
	iE-Extensions								ProtocolExtensionContainer { { E-DPCH-Information-ExtIEs} }		OPTIONAL,
	...
}

E-DPCH-Information-ExtIEs PCAP-PROTOCOL-EXTENSION ::= {
	...
}


Max-Set-E-DPDCHs ::= ENUMERATED {
	vN64, vN32, vN16, vN8, v2xN4, v2xN2, v2xN2plus2xN4,
	...
	}
-- Values related to TS 25.212 [16]

E-TFCS-Information ::= SEQUENCE {
	e-DCH-TFCS-Index								E-DCH-TFCS-Index,
	reference-E-TFCI-Information					Reference-E-TFCI-Information		OPTIONAL,
	iE-Extensions									ProtocolExtensionContainer { {E-TFCS-Information-ExtIEs} }		OPTIONAL,
	...
}

E-TFCS-Information-ExtIEs PCAP-PROTOCOL-EXTENSION ::= {
	...
}

E-DCH-TFCS-Index ::= INTEGER (1..4,...)


Reference-E-TFCI-Information ::= SEQUENCE (SIZE (1..maxNrOfRefETFCIs)) OF Reference-E-TFCI-Information-Item

Reference-E-TFCI-Information-Item ::= SEQUENCE {
	reference-E-TFCI				E-TFCI,
	reference-E-TFCI-PO				Reference-E-TFCI-PO,
	iE-Extensions					ProtocolExtensionContainer { { Reference-E-TFCI-Information-Item-ExtIEs} }		OPTIONAL,
	...
}

Reference-E-TFCI-Information-Item-ExtIEs PCAP-PROTOCOL-EXTENSION ::= {
	...
}

Reference-E-TFCI-PO ::= INTEGER (0.. maxNrOfRefETFCI-PO-QUANTSTEPs)
	-- FFS according to mapping in TS 25.213 [17]

E-TFCI ::= INTEGER (0..127)

E-TTI ::= ENUMERATED {
	e-TTI-2ms,
	e-TTI-10ms,
	...
}

E-DPCCH-PO ::= INTEGER (0..maxNrOfEDPCCH-PO-QUANTSTEPs)

CellParameterID ::= INTEGER (0..127,...)

TFCI-Coding ::= ENUMERATED {
	v4,
	v8,
	v16,
	v32,
	...
}

RepetitionLength ::= INTEGER (1..63)

RepetitionPeriod ::= ENUMERATED {
	v1,
	v2,
	v4,
	v8,
	v16,
	v32,
	v64,
	...
}

TDD-DPCHOffset ::= CHOICE {
	initialOffset		INTEGER (0..255),
	noinitialOffset		INTEGER (0..63)
}

UL-Timeslot-Information ::= SEQUENCE (SIZE (1..maxNrOfULTSs)) OF UL-Timeslot-InformationItem

maxNrOfULTSs				INTEGER ::= 15
UL-Timeslot-InformationItem ::= SEQUENCE {
	timeSlot								TimeSlot,
	midambleShiftAndBurstType				MidambleShiftAndBurstType,
	tFCI-Presence							BOOLEAN,
	uL-Code-InformationList					TDD-UL-Code-Information,
	iE-Extensions							ProtocolExtensionContainer { { UL-Timeslot-InformationItem-ExtIEs} }		OPTIONAL,
	...
}

UL-Timeslot-InformationItem-ExtIEs PCAP-PROTOCOL-EXTENSION ::= {
	...
}


TimeSlot ::= INTEGER (0..14)

MidambleShiftAndBurstType ::=		CHOICE {
	type1								SEQUENCE {
		midambleConfigurationBurstType1And3	MidambleConfigurationBurstType1And3,
		midambleAllocationMode 				CHOICE {
			defaultMidamble						NULL,
			commonMidamble						NULL,
			ueSpecificMidamble					MidambleShiftLong,
			...
		},
	...
	},
	type2								SEQUENCE {
		midambleConfigurationBurstType2		MidambleConfigurationBurstType2,
		midambleAllocationMode 				CHOICE {
			defaultMidamble						NULL,
			commonMidamble						NULL,
			ueSpecificMidamble					MidambleShiftShort,
			...
		},
		...
	},
	type3								SEQUENCE {
		midambleConfigurationBurstType1And3	MidambleConfigurationBurstType1And3,
		midambleAllocationMode 				CHOICE {
			defaultMidamble						NULL,
			ueSpecificMidamble					MidambleShiftLong,
		...
		},
		...
	},
	...
}

MidambleShiftLong ::=				INTEGER (0..15)

MidambleShiftShort ::=				INTEGER (0..5)

MidambleConfigurationBurstType1And3 ::=		ENUMERATED {v4, v8, v16}

MidambleConfigurationBurstType2 ::=		ENUMERATED {v3, v6}

TDD-UL-Code-Information ::= SEQUENCE (SIZE (1..maxNrOfDPCHs)) OF TDD-UL-Code-InformationItem

maxNrOfDPCHs				INTEGER ::= 240

TDD-UL-Code-InformationItem ::= SEQUENCE {
	tdd-ChannelisationCode					TDD-ChannelisationCode,
	iE-Extensions							ProtocolExtensionContainer { { TDD-UL-Code-InformationItem-ExtIEs} }		OPTIONAL,
	...
}

TDD-UL-Code-InformationItem-ExtIEs PCAP-PROTOCOL-EXTENSION ::= {
	...
}

TDD-ChannelisationCode ::= ENUMERATED {
	chCode1div1,
	chCode2div1,
	chCode2div2,
	chCode4div1,
	chCode4div2,
	chCode4div3,
	chCode4div4,
	chCode8div1,
	chCode8div2,
	chCode8div3,
	chCode8div4,
	chCode8div5,
	chCode8div6,
	chCode8div7,
	chCode8div8,
	chCode16div1,
	chCode16div2,
	chCode16div3,
	chCode16div4,
	chCode16div5,
	chCode16div6,
	chCode16div7,
	chCode16div8,
	chCode16div9,
	chCode16div10,
	chCode16div11,
	chCode16div12,
	chCode16div13,
	chCode16div14,
	chCode16div15,
	chCode16div16,
	...
}

SpecialBurstScheduling ::= INTEGER (1..256)	-- Number of frames between special burst transmission during DTX

-- **********************************
--
-- UTDOA Cell Fach Information
--
-- **********************************

UTDOA-CELLFACH ::=	SEQUENCE {
	pRACHparameters							PRACHparameters,
	cRNTI									C-RNTI,
	uschParameters							UschParameters			OPTIONAL,
	iE-Extensions							ProtocolExtensionContainer { { UTDOA-CELLFACH-ExtIEs} } OPTIONAL,
	...
}

UTDOA-CELLFACH-ExtIEs		PCAP-PROTOCOL-EXTENSION ::= {
	...
}

PRACHparameters ::=	SEQUENCE (SIZE (1..maxPRACH)) OF
	PRACH-ChannelInfo


PRACH-ChannelInfo ::= SEQUENCE {
	pRACH-Info					PRACH-Info,
	tFS							TransportFormatSet,
	tFCS						TFCS,
	iE-Extensions				ProtocolExtensionContainer { { PRACH-ChannelInfo-ExtIEs} } OPTIONAL,
	...
}

PRACH-ChannelInfo-ExtIEs		PCAP-PROTOCOL-EXTENSION ::= {
	...
}



PRACH-Info ::=						CHOICE {
		fdd								SEQUENCE {
			availableSignatures					AvailableSignatures,
			availableSF							SF-PRACH,
			preambleScramblingCodeWordNumber	PreambleScramblingCodeWordNumber,
			puncturingLimit						PuncturingLimit,
			availableSubChannelNumbers			AvailableSubChannelNumbers,
			iE-Extensions						ProtocolExtensionContainer { { PRACH-Info-FDD-ExtIEs} } OPTIONAL,
			...
		},
		tdd								SEQUENCE {
			timeSlot								TimeSlot,
			tdd-ChannelisationCode					TDD-ChannelisationCode,
			maxPRACH-MidambleShifts					MaxPRACH-MidambleShifts,
			pRACH-Midamble							PRACH-Midamble,
			iE-Extensions							ProtocolExtensionContainer { { PRACH-Info-TDD-ExtIEs} } OPTIONAL,
			...
		},
		...
}

PRACH-Info-FDD-ExtIEs		PCAP-PROTOCOL-EXTENSION ::= {
	...
}

PRACH-Info-TDD-ExtIEs		PCAP-PROTOCOL-EXTENSION ::= {
	...
}

SF-PRACH ::=						ENUMERATED {
										sfpr32, sfpr64, sfpr128, sfpr256, ... }

AvailableSignatures ::=			BIT STRING {
									signature15(0),
									signature14(1),
									signature13(2),
									signature12(3),
									signature11(4),
									signature10(5),
									signature9(6),
									signature8(7),
									signature7(8),
									signature6(9),
									signature5(10),
									signature4(11),
									signature3(12),
									signature2(13),
									signature1(14),
									signature0(15)
									}	 (SIZE(16))

PreambleScramblingCodeWordNumber ::=	INTEGER (0..15)

PuncturingLimit ::=		INTEGER (0..15)
-- 0: 40%; 1: 44%; ... 14: 96%; 15: 100%


AvailableSubChannelNumbers ::=		BIT STRING {
										subCh11(0),
										subCh10(1),
									 	subCh9(2),
									 	subCh8(3),
									 	subCh7(4),
									 	subCh6(5),
									 	subCh5(6),
									 	subCh4(7),
									 	subCh3(8),
									 	subCh2(9),
									 	subCh1(10),
									 	subCh0(11)
										} 	 (SIZE(12))


ScramblingCodeType ::=				ENUMERATED {
										shortSC,
										longSC }

UL-ScramblingCode ::=				INTEGER (0..16777215)

NumberOfFBI-Bits ::=				INTEGER (0..2)

TransportFormatSet ::=								SEQUENCE {
	dynamicPart				TransportFormatSet-DynamicPartList,
	semi-staticPart			TransportFormatSet-Semi-staticPart,
	iE-Extensions			ProtocolExtensionContainer { { TransportFormatSet-ExtIEs} }		OPTIONAL,
	...
}

TransportFormatSet-ExtIEs PCAP-PROTOCOL-EXTENSION ::= {
	...
}

TransportFormatSet-DynamicPartList ::= SEQUENCE (SIZE (1..maxNrOfTFs)) OF
	SEQUENCE {
		rlc-Size					RLC-Size,
		numberOfTbsTTIList			SEQUENCE (SIZE (1..maxNrOfTFs)) OF	TbsTTIInfo,
		iE-Extensions				ProtocolExtensionContainer { { TransportFormatSet-DynamicPartList-ExtIEs} }		OPTIONAL,
		...
	}

TransportFormatSet-DynamicPartList-ExtIEs PCAP-PROTOCOL-EXTENSION ::= {
	...
}

TbsTTIInfo ::= SEQUENCE {
	tTIInfo				TransportFormatSet-TransmissionTimeIntervalDynamic		OPTIONAL,
	numberOfTbs			TransportFormatSet-NrOfTransportBlocks,
	iE-Extensions		ProtocolExtensionContainer { { TbsTTIInfo-ExtIEs} } OPTIONAL,
	...
}

TbsTTIInfo-ExtIEs PCAP-PROTOCOL-EXTENSION ::= {
	...
}

RLC-Size	::=	INTEGER (129..5055)


TransportFormatSet-NrOfTransportBlocks ::= INTEGER (0..512)


TransportFormatSet-Semi-staticPart ::= SEQUENCE {
	transmissionTimeInterval	 	TransportFormatSet-TransmissionTimeIntervalSemiStatic,
	channelCoding					TransportFormatSet-ChannelCodingType,
	codingRate						TransportFormatSet-CodingRate				OPTIONAL,
	-- This IE shall be present if the Type of channel coding IE is set to 'convolutional' or 'turbo'
	rateMatchingAttribute			TransportFormatSet-RateMatchingAttribute,
	cRC-Size						TransportFormatSet-CRC-Size,
	iE-Extensions					ProtocolExtensionContainer { { TransportFormatSet-Semi-staticPart-ExtIEs} }		OPTIONAL,
	...
}

TransportFormatSet-Semi-staticPart-ExtIEs PCAP-PROTOCOL-EXTENSION ::= {
	...
}

TransportFormatSet-TransmissionTimeIntervalSemiStatic ::= ENUMERATED {
	msec-5,
	msec-10,
	msec-20,
	msec-40,
	msec-80,
	dynamic,
	...
}

TransportFormatSet-ChannelCodingType ::= ENUMERATED {
	no-codingTDD,
	convolutional-coding,
	turbo-coding,
	...
}

TransportFormatSet-CodingRate ::= ENUMERATED {
	half,
	third,
	...
}

TransportFormatSet-RateMatchingAttribute ::= INTEGER (1..maxRateMatching)

TransportFormatSet-CRC-Size ::= ENUMERATED {
	v0,
	v8,
	v12,
	v16,
	v24,
	...
}



TransportFormatSet-TransmissionTimeIntervalDynamic ::= ENUMERATED {
	msec-10,
	msec-20,
	msec-40,
	msec-80,
	dynamic,
	...
}

TFCS ::= 		SEQUENCE (SIZE (1..maxTFC)) OF CTFC

CTFC ::=						CHOICE{
		ctfc2Bit							SEQUENCE (SIZE (1..maxTFC)) OF INTEGER (0..3),
		ctfc4Bit							SEQUENCE (SIZE (1..maxTFC)) OF INTEGER (0..15),
		ctfc6Bit							SEQUENCE (SIZE (1..maxTFC)) OF INTEGER (0..63),
		ctfc8Bit							SEQUENCE (SIZE (1..maxTFC)) OF INTEGER (0..255),
		ctfc12Bit							SEQUENCE (SIZE (1..maxTFC)) OF INTEGER (0..4095),
		ctfc16Bit							SEQUENCE (SIZE (1..maxTFC)) OF INTEGER (0..65535),
		ctfc24Bit							SEQUENCE (SIZE (1..maxTFC)) OF INTEGER (0..16777215),
		...
		}


C-RNTI ::=						BIT STRING (SIZE (16))

UARFCN ::=						INTEGER (0..16383)


CFN ::= INTEGER (0..255)

ChipOffset ::= INTEGER (0..38399)
-- Unit Chip

FrameOffset ::= INTEGER (0..255)

PrimaryScramblingCode ::= INTEGER (0..511)

UschParameters ::=	SEQUENCE {
	cellParameterID						CellParameterID,
	tFCI-Coding							TFCI-Coding,
	punctureLimit						PuncturingLimit,
	repetitionPeriod					RepetitionPeriod,
	uSCH-SchedulingOffset				USCH-SchedulingOffset,
	uL-Timeslot-Information				UL-Timeslot-Information,
	tFCS								TFCS,
	trChInfo							TrChInfoList,
	iE-Extensions						ProtocolExtensionContainer { { UschParameters-ExtIEs} } OPTIONAL,
	...
}

UschParameters-ExtIEs		PCAP-PROTOCOL-EXTENSION ::= {
	...
}


USCH-SchedulingOffset ::= INTEGER (0..255)

MaxPRACH-MidambleShifts ::= ENUMERATED {
	shift4,
	shift8,
	...
}

PRACH-Midamble ::= ENUMERATED {
	inverted,
	direct,
	...
}

--******************************************
--
-- Positioning Response Time
--
--******************************************

Positioning-ResponseTime ::=				ENUMERATED {	ms250, ms500, s1, s2, s3, s4, s6,
															s8, s12, s16, s20, s24, s28, s32, s64,
															...
														}

--******************************************
--
-- Amount of Reporting
--
--******************************************

AmountOfReporting ::=	ENUMERATED { ra2, ra4, ra8, ra16, ra32,
									 ra64, ra-Infinity, ... }



-- **************************************************************
--
-- Include Velocity
--
-- **************************************************************

IncludeVelocity			::= ENUMERATED {
	requested
}


-- **************************************************************
--
-- VelocityEstimate
--
-- **************************************************************

-- VelocityEstimate is based on Description of Velocity in 23.032

VelocityEstimate ::= CHOICE {
	horizontalVelocity								HorizontalVelocity,
	horizontalWithVerticalVelocity					HorizontalWithVerticalVelocity,
	horizontalVelocityWithUncertainty				HorizontalVelocityWithUncertainty,
	horizontalWithVerticalVelocityAndUncertainty	HorizontalWithVerticalVelocityAndUncertainty,
	...
}

HorizontalVelocity	::= SEQUENCE {
	horizontalSpeedAndBearing		HorizontalSpeedAndBearing,
	iE-Extensions		ProtocolExtensionContainer { { HorizontalVelocity-ExtIEs} } OPTIONAL,
	...
}

HorizontalVelocity-ExtIEs PCAP-PROTOCOL-EXTENSION ::= {
	...
}

HorizontalWithVerticalVelocity ::= SEQUENCE {
	horizontalSpeedAndBearing				HorizontalSpeedAndBearing,
	verticalVelocity						VerticalVelocity,
	iE-Extensions							ProtocolExtensionContainer { { HorizontalWithVerticalVelocity-ExtIEs} } OPTIONAL,
	...
}

HorizontalWithVerticalVelocity-ExtIEs PCAP-PROTOCOL-EXTENSION ::= {
	...
}



HorizontalVelocityWithUncertainty ::= SEQUENCE {
	horizontalSpeedAndBearing		HorizontalSpeedAndBearing,
	uncertaintySpeed				INTEGER (0..255),
	iE-Extensions					ProtocolExtensionContainer { { HorizontalVelocityWithUncertainty-ExtIEs} } OPTIONAL,
	...
}

HorizontalVelocityWithUncertainty-ExtIEs PCAP-PROTOCOL-EXTENSION ::= {
	...
}

HorizontalWithVerticalVelocityAndUncertainty ::= SEQUENCE {
	horizontalSpeedAndBearing		HorizontalSpeedAndBearing,
	verticalVelocity				VerticalVelocity,
	horizontalUncertaintySpeed		INTEGER (0..255),
	verticalUncertaintySpeed		INTEGER (0..255),
	iE-Extensions					ProtocolExtensionContainer { { HorizontalWithVerticalVelocityAndUncertainty-ExtIEs} } OPTIONAL,
	...
}

HorizontalWithVerticalVelocityAndUncertainty-ExtIEs PCAP-PROTOCOL-EXTENSION ::= {
	...
}

HorizontalSpeedAndBearing ::= SEQUENCE {
	bearing											INTEGER (0..359),
	horizontalSpeed									INTEGER (0..2047)
}

VerticalVelocity ::= SEQUENCE {
	verticalSpeed									INTEGER (0..255),
	verticalSpeedDirection							VerticalSpeedDirection
}

VerticalSpeedDirection ::= ENUMERATED {
	upward,
	downward
}



--******************************************
--
-- UTRAN-GPS Reference Time
--
--******************************************

UTRAN-GPSReferenceTime ::=	SEQUENCE {
	utran-GPSTimingOfCell		INTEGER (0..2322431999999, ...),
	uC-ID						UC-ID								OPTIONAL,
	sfn							INTEGER (0..4095),
	iE-Extensions				ProtocolExtensionContainer { { UTRAN-GPSReferenceTime-ExtIEs } }	OPTIONAL,
	...
}

UTRAN-GPSReferenceTime-ExtIEs PCAP-PROTOCOL-EXTENSION ::= {
	...
}

--******************************************
--
-- UTRAN-GPS Reference Time Result
--
--******************************************

UTRAN-GPSReferenceTimeResult ::= SEQUENCE {
	ue-GPSTimingOfCell			INTEGER (0..37158911999999, ...),
	uC-ID						UC-ID,
	sfn							INTEGER (0..4095),
	iE-Extensions				ProtocolExtensionContainer { { UTRAN-GPSReferenceTimeResult-ExtIEs } }	OPTIONAL,
	...

}

UTRAN-GPSReferenceTimeResult-ExtIEs PCAP-PROTOCOL-EXTENSION ::= {
	...
}

--******************************************
--
-- UTRAN-GANSS Reference Time Result
--
--******************************************

UTRAN-GANSSReferenceTimeResult ::= SEQUENCE {
	ue-GANSSTimingOfCell		INTEGER (0..345599999999, ...),
	ganss-Time-ID				GANSSID																			OPTIONAL,
	ganssTodUncertainty			INTEGER(0..127)																	OPTIONAL,
	uC-ID						UC-ID,
	sfn							INTEGER (0..4095),
	iE-Extensions				ProtocolExtensionContainer { { UTRAN-GANSSReferenceTimeResult-ExtIEs } }	OPTIONAL,
	...

}

UTRAN-GANSSReferenceTimeResult-ExtIEs PCAP-PROTOCOL-EXTENSION ::= {
	...
}


END

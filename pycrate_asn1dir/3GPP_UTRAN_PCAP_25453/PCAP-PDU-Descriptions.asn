-- **************************************************************
--
-- Elementary Procedure definitions
--
-- **************************************************************

PCAP-PDU-Descriptions {
itu-t (0) identified-organization (4) etsi (0) mobileDomain (0)
umts-Access (20) modules (3) pcap(4) version1 (1) pcap-PDU-Descriptions (0)}

DEFINITIONS AUTOMATIC TAGS ::=

BEGIN

-- **************************************************************
--
-- IE parameter types from other modules.
--
-- **************************************************************

IMPORTS
	Criticality,
	ProcedureCode,
	TransactionID
FROM PCAP-CommonDataTypes

	PositionCalculationRequest,
	PositionCalculationResponse,
	PositionCalculationFailure,
	InformationExchangeInitiationRequest,
	InformationExchangeInitiationResponse,
	InformationExchangeInitiationFailure,
	InformationReport,
	InformationExchangeTerminationRequest,
	InformationExchangeFailureIndication,
	ErrorIndication,
	PrivateMessage,
	PositionInitiationRequest,
	PositionInitiationResponse,
	PositionInitiationFailure,
	PositionActivationRequest,
	PositionActivationResponse,
	PositionActivationFailure,
	PositionParameterModification,
	Abort,
	PositionPeriodicReport,
	PositionPeriodicResult,
	PositionPeriodicTermination

FROM PCAP-PDU-Contents

	id-PositionCalculation,
	id-InformationExchangeInitiation,
	id-InformationReporting,
	id-InformationExchangeTermination,
	id-InformationExchangeFailure,
	id-ErrorIndication,
	id-privateMessage,
	id-PositionInitiation,
	id-PositionActivation,
	id-PositionParameterModification,
	id-Abort,
	id-PositionPeriodicReport,
	id-PositionPeriodicResult,
	id-PositionPeriodicTermination

FROM PCAP-Constants;

-- **************************************************************
--
-- Interface Elementary Procedure Class
--
-- **************************************************************

PCAP-ELEMENTARY-PROCEDURE ::= CLASS {
	&InitiatingMessage			,
	&SuccessfulOutcome			OPTIONAL,
	&UnsuccessfulOutcome		OPTIONAL,
	&Outcome					OPTIONAL,
	&procedureCode				ProcedureCode 	UNIQUE,
	&criticality				Criticality 	DEFAULT ignore
}

WITH SYNTAX {
	INITIATING MESSAGE			&InitiatingMessage
	[SUCCESSFUL OUTCOME			&SuccessfulOutcome]
	[UNSUCCESSFUL OUTCOME		&UnsuccessfulOutcome]
	[OUTCOME					&Outcome]
	PROCEDURE CODE				&procedureCode
	[CRITICALITY				&criticality]
}

-- **************************************************************
--
-- Interface PDU definitions
--
-- **************************************************************

PCAP-PDU ::= CHOICE {
	initiatingMessage		InitiatingMessage,
	successfulOutcome		SuccessfulOutcome,
	unsuccessfulOutcome		UnsuccessfulOutcome,
	outcome					Outcome,
	...
}


InitiatingMessage ::= SEQUENCE {
	procedureCode	PCAP-ELEMENTARY-PROCEDURE.&procedureCode		({PCAP-ELEMENTARY-PROCEDURES}),
	criticality		PCAP-ELEMENTARY-PROCEDURE.&criticality			({PCAP-ELEMENTARY-PROCEDURES}{@procedureCode}),
	transactionID 	TransactionID,
	value			PCAP-ELEMENTARY-PROCEDURE.&InitiatingMessage	({PCAP-ELEMENTARY-PROCEDURES}{@procedureCode})
}

SuccessfulOutcome ::= SEQUENCE {
	procedureCode	PCAP-ELEMENTARY-PROCEDURE.&procedureCode		({PCAP-ELEMENTARY-PROCEDURES}),
	criticality		PCAP-ELEMENTARY-PROCEDURE.&criticality			({PCAP-ELEMENTARY-PROCEDURES}{@procedureCode}),
	transactionID 	TransactionID,
	value			PCAP-ELEMENTARY-PROCEDURE.&SuccessfulOutcome	({PCAP-ELEMENTARY-PROCEDURES}{@procedureCode})
}

UnsuccessfulOutcome ::= SEQUENCE {
	procedureCode	PCAP-ELEMENTARY-PROCEDURE.&procedureCode		({PCAP-ELEMENTARY-PROCEDURES}),
	criticality		PCAP-ELEMENTARY-PROCEDURE.&criticality			({PCAP-ELEMENTARY-PROCEDURES}{@procedureCode}),
	transactionID 	TransactionID,
	value			PCAP-ELEMENTARY-PROCEDURE.&UnsuccessfulOutcome	({PCAP-ELEMENTARY-PROCEDURES}{@procedureCode})
}

Outcome ::= SEQUENCE {
	procedureCode	PCAP-ELEMENTARY-PROCEDURE.&procedureCode		({PCAP-ELEMENTARY-PROCEDURES}),
	criticality		PCAP-ELEMENTARY-PROCEDURE.&criticality			({PCAP-ELEMENTARY-PROCEDURES}{@procedureCode}),
	transactionID 	TransactionID,
	value			PCAP-ELEMENTARY-PROCEDURE.&Outcome				({PCAP-ELEMENTARY-PROCEDURES}{@procedureCode})
}

-- **************************************************************
--
-- Interface Elementary Procedure List
--
-- **************************************************************

PCAP-ELEMENTARY-PROCEDURES PCAP-ELEMENTARY-PROCEDURE ::= {
	PCAP-ELEMENTARY-PROCEDURES-CLASS-1	|
	PCAP-ELEMENTARY-PROCEDURES-CLASS-2	,
	...
}

PCAP-ELEMENTARY-PROCEDURES-CLASS-1 PCAP-ELEMENTARY-PROCEDURE ::= {
	positionCalculation				|
	informationExchangeInitiation,
	...,
	positionInitiation |
	positionActivation

}


PCAP-ELEMENTARY-PROCEDURES-CLASS-2 PCAP-ELEMENTARY-PROCEDURE ::= {
	informationReporting			|
	informationExchangeTermination	|
	informationExchangeFailure		|
	errorIndication					|
	privateMessage,
	...,
	positionParameterModification 	|
	abort							|
	positionPeriodicReport			|
	positionPeriodicResult			|
	positionPeriodicTermination
}


-- **************************************************************
--
-- Interface Elementary Procedures
--
-- **************************************************************

positionCalculation PCAP-ELEMENTARY-PROCEDURE ::= {
	INITIATING MESSAGE		PositionCalculationRequest
	SUCCESSFUL OUTCOME		PositionCalculationResponse
	UNSUCCESSFUL OUTCOME	PositionCalculationFailure
	PROCEDURE CODE			id-PositionCalculation
	CRITICALITY				reject
}


informationExchangeInitiation PCAP-ELEMENTARY-PROCEDURE ::= {
	INITIATING MESSAGE		InformationExchangeInitiationRequest
	SUCCESSFUL OUTCOME		InformationExchangeInitiationResponse
	UNSUCCESSFUL OUTCOME	InformationExchangeInitiationFailure
	PROCEDURE CODE			id-InformationExchangeInitiation
	CRITICALITY				reject
}

positionInitiation PCAP-ELEMENTARY-PROCEDURE ::= {
	INITIATING MESSAGE		PositionInitiationRequest
	SUCCESSFUL OUTCOME		PositionInitiationResponse
	UNSUCCESSFUL OUTCOME	PositionInitiationFailure
	PROCEDURE CODE			id-PositionInitiation
	CRITICALITY				reject
}

positionActivation PCAP-ELEMENTARY-PROCEDURE ::= {
	INITIATING MESSAGE		PositionActivationRequest
	SUCCESSFUL OUTCOME		PositionActivationResponse
	UNSUCCESSFUL OUTCOME	PositionActivationFailure
	PROCEDURE CODE			id-PositionActivation
	CRITICALITY				reject
}


informationReporting PCAP-ELEMENTARY-PROCEDURE ::= {
	INITIATING MESSAGE		InformationReport
	PROCEDURE CODE			id-InformationReporting
	CRITICALITY				ignore
}


informationExchangeTermination PCAP-ELEMENTARY-PROCEDURE ::= {
	INITIATING MESSAGE		InformationExchangeTerminationRequest
	PROCEDURE CODE			id-InformationExchangeTermination
	CRITICALITY				ignore
}


informationExchangeFailure PCAP-ELEMENTARY-PROCEDURE ::= {
	INITIATING MESSAGE		InformationExchangeFailureIndication
	PROCEDURE CODE			id-InformationExchangeFailure
	CRITICALITY				ignore
}


errorIndication PCAP-ELEMENTARY-PROCEDURE ::= {
	INITIATING MESSAGE		ErrorIndication
	PROCEDURE CODE			id-ErrorIndication
	CRITICALITY				ignore
}

privateMessage PCAP-ELEMENTARY-PROCEDURE ::= {
	INITIATING MESSAGE		PrivateMessage
	PROCEDURE CODE			id-privateMessage
	CRITICALITY				ignore
}

positionParameterModification PCAP-ELEMENTARY-PROCEDURE ::= {
	INITIATING MESSAGE		PositionParameterModification
	PROCEDURE CODE			id-PositionParameterModification
	CRITICALITY				ignore
}


abort PCAP-ELEMENTARY-PROCEDURE ::= {
	INITIATING MESSAGE		Abort
	PROCEDURE CODE			id-Abort
	CRITICALITY				ignore
}

positionPeriodicReport PCAP-ELEMENTARY-PROCEDURE ::= {
	INITIATING MESSAGE		PositionPeriodicReport
	PROCEDURE CODE			id-PositionPeriodicReport
	CRITICALITY				ignore
}

positionPeriodicResult PCAP-ELEMENTARY-PROCEDURE ::= {
	INITIATING MESSAGE		PositionPeriodicResult
	PROCEDURE CODE			id-PositionPeriodicResult
	CRITICALITY				ignore
}

positionPeriodicTermination PCAP-ELEMENTARY-PROCEDURE ::= {
	INITIATING MESSAGE		PositionPeriodicTermination
	PROCEDURE CODE			id-PositionPeriodicTermination
	CRITICALITY				ignore
}

END

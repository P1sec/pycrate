-- ASN1START
-- **************************************************************
--
-- Information Element Definitions
--
-- **************************************************************

F1AP-IEs {
itu-t (0) identified-organization (4) etsi (0) mobileDomain (0)
ngran-access (22) modules (3) f1ap (3) version1 (1) f1ap-IEs (2) }

DEFINITIONS AUTOMATIC TAGS ::=

BEGIN

IMPORTS
	id-gNB-CUSystemInformation,
	id-HandoverPreparationInformation,
	id-TAISliceSupportList,
	id-RANAC,
	id-BearerTypeChange,
	id-Cell-Direction,
	id-Cell-Type,
	id-CellGroupConfig,
	id-AvailablePLMNList,
	id-PDUSessionID,
	id-ULPDUSessionAggregateMaximumBitRate,
	id-DC-Based-Duplication-Configured,
	id-DC-Based-Duplication-Activation,
	id-Duplication-Activation,
	id-DLPDCPSNLength,
	id-ULPDCPSNLength,
	id-RLC-Status,
	id-MeasurementTimingConfiguration,
	id-DRB-Information,
	id-QoSFlowMappingIndication,
	id-ServingCellMO,
	id-RLCMode,
	id-ExtendedServedPLMNs-List,
	id-ExtendedAvailablePLMN-List,
	id-DRX-LongCycleStartOffset,
	id-SelectedBandCombinationIndex,
	id-SelectedFeatureSetEntryIndex,
	id-Ph-InfoSCG,
	id-latest-RRC-Version-Enhanced,
	id-RequestedBandCombinationIndex,
	id-RequestedFeatureSetEntryIndex,
	id-DRX-Config,
	id-UEAssistanceInformation,
	id-PDCCH-BlindDetectionSCG,
	id-Requested-PDCCH-BlindDetectionSCG,
	id-BPLMN-ID-Info-List,
	id-NotificationInformation,
	id-TNLAssociationTransportLayerAddressgNBDU,
	id-portNumber,
	id-AdditionalSIBMessageList,
	id-IgnorePRACHConfiguration,
	id-CG-Config,
	id-Ph-InfoMCG,
	id-AggressorgNBSetID,
	id-VictimgNBSetID,
	id-MeasGapSharingConfig,
	id-systemInformationAreaID,
	id-areaScope,
	id-IntendedTDD-DL-ULConfig,
	id-QosMonitoringRequest,
	id-BHInfo,
	id-IAB-Info-IAB-DU,
	id-IAB-Info-IAB-donor-CU,
	id-IAB-Barred,
	id-SIB12-message,
	id-SIB13-message,
	id-SIB14-message,
	id-UEAssistanceInformationEUTRA,
	id-SL-PHY-MAC-RLC-Config,
	id-SL-ConfigDedicatedEUTRA-Info,
	id-AlternativeQoSParaSetList,
	id-CurrentQoSParaSetIndex,
	id-CarrierList,
	id-ULCarrierList,
	id-FrequencyShift7p5khz,
	id-SSB-PositionsInBurst,
	id-NRPRACHConfig,
	id-TDD-UL-DLConfigCommonNR,
	id-CNPacketDelayBudgetDownlink,
	id-CNPacketDelayBudgetUplink,
	id-ExtendedPacketDelayBudget,
	id-TSCTrafficCharacteristics,
	id-AdditionalPDCPDuplicationTNL-List,
	id-RLCDuplicationInformation,
	id-AdditionalDuplicationIndication,
	id-mdtConfiguration,
	id-TraceCollectionEntityURI,
	id-NID,
	id-NPNSupportInfo,
	id-NPNBroadcastInformation,
	id-AvailableSNPN-ID-List,
	id-SIB10-message,
	id-RequestedP-MaxFR2,
	id-DLCarrierList,
	id-ExtendedTAISliceSupportList,
	id-E-CID-MeasurementQuantities-Item,
	id-ConfiguredTACIndication,
	id-NRCGI,
	id-SFN-Offset,
	id-TransmissionStopIndicator,
	id-SrsFrequency,
	id-EstimatedArrivalProbability,
	id-Supported-MBS-FSA-ID-List,
	id-TRPType,
	id-SRSSpatialRelationPerSRSResource,
	id-MBS-Broadcast-NeighbourCellList,
	id-PDCPTerminatingNodeDLTNLAddrInfo,
	id-ENBDLTNLAddress,
	id-PRS-Resource-ID,
	id-LocationMeasurementInformation,
	id-SliceRadioResourceStatus,
	id-CompositeAvailableCapacity-SUL,
	id-NR-U,
	id-NR-U-Channel-List,
	id-MIMOPRBusageInformation,
	id-IngressNonF1terminatingTopologyIndicator,
	id-NonF1terminatingTopologyIndicator,
	id-EgressNonF1terminatingTopologyIndicator,
	id-rBSetConfiguration,
	id-frequency-Domain-HSNA-Configuration-List,
	id-child-IAB-Nodes-NA-Resource-List,
	id-Parent-IAB-Nodes-NA-Resource-Configuration-List,
	id-uL-FreqInfo,
	id-uL-Transmission-Bandwidth,
	id-dL-FreqInfo,
	id-dL-Transmission-Bandwidth,
	id-uL-NR-Carrier-List,
	id-dL-NR-Carrier-List,
	id-nRFreqInfo,
	id-transmission-Bandwidth,
	id-nR-Carrier-List,
	id-permutation,
	id-M5ReportAmount,
	id-M6ReportAmount,
	id-M7ReportAmount,
	id-SurvivalTime,
	id-PDCMeasurementQuantities-Item,
	id-OnDemandPRS,
	id-AoA-SearchWindow,
	id-ZoAInformation,
	id-ARPLocationInfo,
	id-ARP-ID,
	id-MultipleULAoA,
	id-UL-SRS-RSRPP,
	id-SRSResourcetype,
	id-ExtendedAdditionalPathList,
	id-LoS-NLoSInformation,
	id-NumberOfTRPRxTEG,
	id-NumberOfTRPRxTxTEG,
	id-TRPTxTEGAssociation,
	id-TRPTEGInformation,
	id-TRPRx-TEGInformation,
	id-TRPBeamAntennaInformation,
	id-Redcap-Bcast-Information,
	id-NR-TADV,
	id-SDT-MAC-PHY-CG-Config,
	id-CG-SDTindicatorSetup,
	id-CG-SDTindicatorMod,
	id-SDTRLCBearerConfiguration,
	id-SRBMappingInfo,
	id-DRBMappingInfo,
	id-LastUsedCellIndication,
	id-SIB17-message,
	id-MUSIM-GapConfig,
	id-SIB20-message,
	id-pathPower,
	id-DU-RX-MT-RX-Extend,
	id-DU-TX-MT-TX-Extend,
	id-DU-RX-MT-TX-Extend,
	id-DU-TX-MT-RX-Extend,
	id-TAINSAGSupportList,
	id-SL-RLC-ChannelToAddModList,
	id-SIB15-message,
	id-InterFrequencyConfig-NoGap,
	id-MBSInterestIndication,
	id-L571Info,
	id-L1151Info,
	id-SCS-480,
	id-SCS-960,
	id-SRSPortIndex,
	id-PEISubgroupingSupportIndication,
	id-NeedForGapsInfoNR,
	id-NeedForGapNCSGInfoNR,
	id-NeedForGapNCSGInfoEUTRA,
	id-Source-MRB-ID,
	id-RedCapIndication,
	id-UL-GapFR2-Config,
	id-ConfigRestrictInfoDAPS,
	id-MulticastF1UContextReferenceCU,
	id-TwoPHRModeMCG,
	id-TwoPHRModeSCG,
	maxNRARFCN,
	maxnoofErrors,
	maxnoofBPLMNs,
	maxnoofBPLMNsNR,
	maxnoofDLUPTNLInformation,
	maxnoofNrCellBands,
	maxnoofULUPTNLInformation,
	maxnoofQoSFlows,
	maxnoofSliceItems,
	maxnoofSIBTypes,
	maxnoofSITypes,
	maxCellineNB,
	maxnoofExtendedBPLMNs,
	maxnoofAdditionalSIBs,
	maxnoofUACPLMNs,
	maxnoofUACperPLMN,
	maxCellingNBDU,
	maxnoofTLAs,
	maxnoofGTPTLAs,
	maxnoofslots,
	maxnoofNonUPTrafficMappings,
	maxnoofServingCells,
	maxnoofServedCellsIAB,
	maxnoofChildIABNodes,
	maxnoofIABSTCInfo,
	maxnoofSymbols,
	maxnoofDUFSlots,
	maxnoofHSNASlots,
	maxnoofEgressLinks,
	maxnoofMappingEntries,
	maxnoofDSInfo,
	maxnoofQoSParaSets,
	maxnoofPC5QoSFlows,
	maxnoofSSBAreas,
	maxnoofNRSCSs,
	maxnoofPhysicalResourceBlocks,
	maxnoofPhysicalResourceBlocks-1,
	maxnoofPRACHconfigs,
	maxnoofRACHReports,
	maxnoofRLFReports,
	maxnoofAdditionalPDCPDuplicationTNL,
	maxnoofRLCDuplicationState,
	maxnoofCHOcells,
	maxnoofMDTPLMNs,
	maxnoofCAGsupported,
	maxnoofNIDsupported,
	maxnoofExtSliceItems,
	maxnoofPosMeas,
	maxnoofTRPInfoTypes,
	maxnoofSRSTriggerStates,
	maxnoofSpatialRelations,
	maxnoBcastCell,
	maxnoofTRPs,
	maxnoofAngleInfo,
	maxnooflcs-gcs-translation,
	maxnoofPath,
	maxnoofMeasE-CID,
	maxnoofSSBs,
	maxnoSRS-ResourceSets,
	maxnoSRS-ResourcePerSet,
	maxnoSRS-Carriers,
	maxnoSCSs,
	maxnoSRS-Resources,
	maxnoSRS-PosResources,
	maxnoSRS-PosResourceSets,
	maxnoSRS-PosResourcePerSet,
	maxnoofPRS-ResourceSets,
	maxnoofPRS-ResourcesPerSet,
	maxNoOfMeasTRPs,
	maxnoofPRSresourceSets,
	maxnoofPRSresources,
	maxnoofSuccessfulHOReports,
	maxnoofNR-UChannelIDs,
	maxServedCellforSON,
	maxNeighbourCellforSON,
	maxAffectedCells,
	maxnoofMBSQoSFlows,
	maxnoofMBSFSAs,
	maxnoofMBSAreaSessionIDs,
	maxnoofMBSServiceAreaInformation,
	maxnoofTAIforMBS,
	maxnoofCellsforMBS,
	maxnoofIABCongInd,
	maxnoofBHRLCChannels,
	maxnoofTLAsIAB,
	maxnoofRBsetsPerCell,
	maxnoofRBsetsPerCell-1,
	maxnoofNeighbourNodeCellsIAB,
	maxnoofMeasPDC,
	maxnoARPs,
	maxnoofULAoAs,
	maxNoPathExtended,
	maxnoTRPTEGs,
	maxFreqLayers,
	maxNumResourcesPerAngle,
	maxnoAzimuthAngles,
	maxnoElevationAngles,
	maxnoofPRSTRPs,
	maxnoofQoEInformation,
	maxnoofUuRLCChannels,
	maxnoofPC5RLCChannels,
	maxnoofSMBRValues,
	maxnoofMBSSessionsofUE,
	maxnoofSLdestinations,
	maxnoofNSAGs,
	maxnoofSDTBearers,
	maxnoofPosSITypes,
	maxnoofMRBs,
	maxNrofBWPs


FROM F1AP-Constants

	Criticality,
	ProcedureCode,
	ProtocolIE-ID,
	TriggeringMessage

FROM F1AP-CommonDataTypes

	ProtocolExtensionContainer{},
	F1AP-PROTOCOL-EXTENSION,
	ProtocolIE-SingleContainer{},
	F1AP-PROTOCOL-IES

FROM F1AP-Containers;

-- A

AbortTransmission ::= CHOICE {
	sRSResourceSetID		SRSResourceSetID,
	releaseALL				NULL,
	choice-extension		ProtocolIE-SingleContainer { { AbortTransmission-ExtIEs } }
}

AbortTransmission-ExtIEs F1AP-PROTOCOL-IES ::= {
	...
}

AccessPointPosition ::= SEQUENCE {
	latitudeSign				ENUMERATED {north, south},
	latitude					INTEGER (0..8388607),
	longitude					INTEGER (-8388608..8388607),
	directionOfAltitude			ENUMERATED {height, depth},
	altitude					INTEGER (0..32767),
	uncertaintySemi-major		INTEGER (0..127),
	uncertaintySemi-minor		INTEGER (0..127),
	orientationOfMajorAxis		INTEGER (0..179),
	uncertaintyAltitude			INTEGER (0..127),
	confidence					INTEGER (0..100),
	iE-Extensions				ProtocolExtensionContainer { { AccessPointPosition-ExtIEs} } OPTIONAL
}

AccessPointPosition-ExtIEs F1AP-PROTOCOL-EXTENSION ::= {
	...
}

Activated-Cells-to-be-Updated-List ::= SEQUENCE (SIZE(1..maxnoofServedCellsIAB)) OF Activated-Cells-to-be-Updated-List-Item

Activated-Cells-to-be-Updated-List-Item ::=	SEQUENCE{
	nRCGI								NRCGI,
	iAB-DU-Cell-Resource-Configuration-Mode-Info	IAB-DU-Cell-Resource-Configuration-Mode-Info,
	iE-Extensions						ProtocolExtensionContainer { { Activated-Cells-to-be-Updated-List-Item-ExtIEs} } OPTIONAL
}

Activated-Cells-to-be-Updated-List-Item-ExtIEs F1AP-PROTOCOL-EXTENSION ::= {
	...
}

ActivationRequestType ::= ENUMERATED {activate, deactivate, ...}

ActiveULBWP  ::= SEQUENCE {
	locationAndBandwidth		INTEGER (0..37949,...),
	subcarrierSpacing           ENUMERATED {kHz15, kHz30, kHz60, kHz120,...},
	cyclicPrefix				ENUMERATED {normal, extended},
	txDirectCurrentLocation		INTEGER (0..3301,...),
	shift7dot5kHz				ENUMERATED {true, ...} OPTIONAL,
	sRSConfig					SRSConfig,
	iE-Extensions					ProtocolExtensionContainer { { ActiveULBWP-ExtIEs} } OPTIONAL
}

ActiveULBWP-ExtIEs F1AP-PROTOCOL-EXTENSION ::= {
	...
}

AdditionalDuplicationIndication ::= ENUMERATED {
	three,
	four,
	...
}


AdditionalPath-List::= SEQUENCE (SIZE(1..maxnoofPath)) OF AdditionalPath-Item

AdditionalPath-Item ::=SEQUENCE {
	relativePathDelay	RelativePathDelay,
	pathQuality			TRPMeasurementQuality 	OPTIONAL,
	iE-Extensions		ProtocolExtensionContainer { { AdditionalPath-Item-ExtIEs } }	OPTIONAL
}

AdditionalPath-Item-ExtIEs 	F1AP-PROTOCOL-EXTENSION ::= {
	{ ID id-MultipleULAoA	CRITICALITY ignore EXTENSION MultipleULAoA		PRESENCE optional}|
	{ ID id-pathPower		CRITICALITY ignore EXTENSION UL-SRS-RSRPP		PRESENCE optional},
	...
}

ExtendedAdditionalPathList ::= SEQUENCE (SIZE (1.. maxNoPathExtended)) OF ExtendedAdditionalPathList-Item


ExtendedAdditionalPathList-Item ::= SEQUENCE {
	relativeTimeOfPath	RelativePathDelay,
	pathQuality			TRPMeasurementQuality	OPTIONAL,
	multipleULAoA		MultipleULAoA  			OPTIONAL,
	pathPower			UL-SRS-RSRPP			OPTIONAL,
	iE-Extensions		ProtocolExtensionContainer { { ExtendedAdditionalPathList-Item-ExtIEs} } OPTIONAL,
	...
}

ExtendedAdditionalPathList-Item-ExtIEs F1AP-PROTOCOL-EXTENSION ::= {
	...
}

AdditionalPDCPDuplicationTNL-List ::= SEQUENCE (SIZE(1..maxnoofAdditionalPDCPDuplicationTNL)) OF AdditionalPDCPDuplicationTNL-Item

AdditionalPDCPDuplicationTNL-Item ::=SEQUENCE {
	additionalPDCPDuplicationUPTNLInformation		UPTransportLayerInformation,
	iE-Extensions	ProtocolExtensionContainer { { AdditionalPDCPDuplicationTNL-ItemExtIEs } }	OPTIONAL,
	...
}

AdditionalPDCPDuplicationTNL-ItemExtIEs 	F1AP-PROTOCOL-EXTENSION ::= {
{ ID id-BHInfo		CRITICALITY ignore	EXTENSION BHInfo		PRESENCE optional	},
	...
}

AdditionalSIBMessageList ::= SEQUENCE (SIZE(1..maxnoofAdditionalSIBs)) OF AdditionalSIBMessageList-Item

AdditionalSIBMessageList-Item ::= SEQUENCE {
	additionalSIB			OCTET STRING,
	iE-Extensions		ProtocolExtensionContainer { { AdditionalSIBMessageList-Item-ExtIEs} } OPTIONAL
}

AdditionalSIBMessageList-Item-ExtIEs F1AP-PROTOCOL-EXTENSION ::= {
	...
}

AdditionalRRMPriorityIndex ::= BIT STRING (SIZE(32))

AffectedCellsAndBeams-List ::= SEQUENCE (SIZE (1.. maxAffectedCells)) OF AffectedCellsAndBeams-Item

AffectedCellsAndBeams-Item::= SEQUENCE {
	nRCGI					NRCGI,
	affectedSSB-List		AffectedSSB-List OPTIONAL,
	iE-Extensions		ProtocolExtensionContainer { { AffectedCellsAndBeams-Item-ExtIEs} } OPTIONAL,
	...
}
AffectedCellsAndBeams-Item-ExtIEs F1AP-PROTOCOL-EXTENSION ::= {
	...
}


AffectedSSB-List::= SEQUENCE (SIZE (1..maxnoofSSBAreas)) OF AffectedSSB-Item

AffectedSSB-Item::= SEQUENCE {
	sSB-Index	INTEGER(0..63),
	iE-Extensions		ProtocolExtensionContainer { { AffectedSSB-Item-ExtIEs} } OPTIONAL,
	...
}
AffectedSSB-Item-ExtIEs F1AP-PROTOCOL-EXTENSION ::= {
	...
}


AggressorCellList ::= SEQUENCE (SIZE(1..maxCellingNBDU)) OF AggressorCellList-Item

AggressorCellList-Item ::= SEQUENCE {
	aggressorCell-ID		NRCGI,
	iE-Extensions	ProtocolExtensionContainer { { AggressorCellList-Item-ExtIEs } }		OPTIONAL
}

AggressorCellList-Item-ExtIEs 	F1AP-PROTOCOL-EXTENSION ::= {
	...
}

AggressorgNBSetID ::= SEQUENCE {
	aggressorgNBSetID		GNBSetID,
	iE-Extensions	ProtocolExtensionContainer { { AggressorgNBSetID-ExtIEs } }	OPTIONAL
}

AggressorgNBSetID-ExtIEs 	F1AP-PROTOCOL-EXTENSION ::= {
	...
}

AllocationAndRetentionPriority ::= SEQUENCE {
	priorityLevel				PriorityLevel,
	pre-emptionCapability		Pre-emptionCapability,
	pre-emptionVulnerability	Pre-emptionVulnerability,
	iE-Extensions				ProtocolExtensionContainer { {AllocationAndRetentionPriority-ExtIEs} } OPTIONAL,
	...
}

AllocationAndRetentionPriority-ExtIEs F1AP-PROTOCOL-EXTENSION ::= {
	...
}

AlternativeQoSParaSetList ::= SEQUENCE (SIZE(1..maxnoofQoSParaSets)) OF AlternativeQoSParaSetItem

AlternativeQoSParaSetItem ::= SEQUENCE {
	alternativeQoSParaSetIndex			QoSParaSetIndex,
	guaranteedFlowBitRateDL				BitRate					OPTIONAL,
	guaranteedFlowBitRateUL				BitRate					OPTIONAL,
	packetDelayBudget					PacketDelayBudget		OPTIONAL,
	packetErrorRate						PacketErrorRate			OPTIONAL,
	iE-Extensions						ProtocolExtensionContainer { {AlternativeQoSParaSetItem-ExtIEs} }	OPTIONAL,
	...
}

AlternativeQoSParaSetItem-ExtIEs F1AP-PROTOCOL-EXTENSION ::= {
	...
}


AngleMeasurementQuality ::= SEQUENCE {
	azimuthQuality	INTEGER(0..255),
	zenithQuality	INTEGER(0..255) OPTIONAL,
	resolution		ENUMERATED{deg0dot1,...},
	iE-Extensions	ProtocolExtensionContainer { { AngleMeasurementQuality-ExtIEs } }	OPTIONAL
}

AngleMeasurementQuality-ExtIEs 	F1AP-PROTOCOL-EXTENSION ::= {
	...
}


AperiodicSRSResourceTriggerList ::= SEQUENCE (SIZE(1..maxnoofSRSTriggerStates)) OF AperiodicSRSResourceTrigger

AperiodicSRSResourceTrigger ::= INTEGER (1..3)

Associated-SCell-Item ::= SEQUENCE {
	sCell-ID		NRCGI,
	iE-Extensions	ProtocolExtensionContainer { { Associated-SCell-ItemExtIEs } }	OPTIONAL
}

Associated-SCell-ItemExtIEs 	F1AP-PROTOCOL-EXTENSION ::= {
	...
}

AvailablePLMNList ::= SEQUENCE (SIZE(1..maxnoofBPLMNs)) OF AvailablePLMNList-Item

AvailablePLMNList-Item ::= SEQUENCE {
	pLMNIdentity			PLMN-Identity,
	iE-Extensions		ProtocolExtensionContainer { { AvailablePLMNList-Item-ExtIEs} } OPTIONAL
}

AvailablePLMNList-Item-ExtIEs F1AP-PROTOCOL-EXTENSION ::= {
	...
}

AvailableSNPN-ID-List ::= SEQUENCE (SIZE(1..maxnoofNIDsupported)) OF AvailableSNPN-ID-List-Item

AvailableSNPN-ID-List-Item ::= SEQUENCE {
	pLMN-Identity				PLMN-Identity,
	availableNIDList			BroadcastNIDList,
	iE-Extensions				ProtocolExtensionContainer { { AvailableSNPN-ID-List-ItemExtIEs} } OPTIONAL,
	...
}

AvailableSNPN-ID-List-ItemExtIEs F1AP-PROTOCOL-EXTENSION ::= {
	...
}

AveragingWindow  ::= INTEGER (0..4095, ...)

AreaScope ::= ENUMERATED {true, ...}

AoA-AssistanceInfo ::= SEQUENCE {
	angleMeasurement			AngleMeasurementType,
	lCS-to-GCS-Translation	LCS-to-GCS-Translation		OPTIONAL,
	iE-Extensions				ProtocolExtensionContainer { { AoA-AssistanceInfo-ExtIEs } } OPTIONAL,
	...
}

AoA-AssistanceInfo-ExtIEs F1AP-PROTOCOL-EXTENSION ::= {
	...
}

AngleMeasurementType ::= CHOICE {
	expected-ULAoA		Expected-UL-AoA,
	expected-ZoA		Expected-ZoA-only,
	choice-extension ProtocolIE-SingleContainer { { AngleMeasurementType-ExtIEs } }
}

AngleMeasurementType-ExtIEs F1AP-PROTOCOL-IES ::= {
...
}

AppLayerBufferLevelList ::= OCTET STRING

ARP-ID ::= INTEGER (1..16, ...)

ARPLocationInformation ::= SEQUENCE (SIZE (1..maxnoARPs)) OF ARPLocationInformation-Item

ARPLocationInformation-Item ::= SEQUENCE {
	aRP-ID				ARP-ID,
	aRPLocationType		ARPLocationType,
	iE-Extensions		ProtocolExtensionContainer { { ARPLocationInformation-ExtIEs} } OPTIONAL,
...
}

ARPLocationInformation-ExtIEs F1AP-PROTOCOL-EXTENSION ::= {
	...
}

ARPLocationType ::= CHOICE {
	aRPPositionRelativeGeodetic			RelativeGeodeticLocation,
	aRPPositionRelativeCartesian		RelativeCartesianLocation,
	choice-extension					ProtocolIE-SingleContainer { { ARPLocationType-ExtIEs } }
}

ARPLocationType-ExtIEs F1AP-PROTOCOL-IES ::= {
	...
}


-- B

BAP-Header-Rewriting-Added-List-Item::= SEQUENCE {
	ingressBAPRoutingID		BAPRoutingID,
	egressBAPRoutingID		BAPRoutingID,
	nonF1terminatingTopologyIndicator		NonF1terminatingTopologyIndicator		OPTIONAL,
	iE-Extensions			ProtocolExtensionContainer { { BAP-Header-Rewriting-Added-List-Item-ExtIEs} }	OPTIONAL
}

BAP-Header-Rewriting-Added-List-Item-ExtIEs F1AP-PROTOCOL-EXTENSION ::= {
	...
}

BAP-Header-Rewriting-Removed-List-Item::= SEQUENCE {
	ingressBAPRoutingID		BAPRoutingID,
	iE-Extensions			ProtocolExtensionContainer { { BAP-Header-Rewriting-Removed-List-Item-ExtIEs} } OPTIONAL
}

BAP-Header-Rewriting-Removed-List-Item-ExtIEs F1AP-PROTOCOL-EXTENSION ::= {
	...
}


BandwidthSRS ::= CHOICE {
	fR1								FR1-Bandwidth,
	fR2								FR2-Bandwidth,
	choice-extension				ProtocolIE-SingleContainer {{ BandwidthSRS-ExtIEs }}
}

BandwidthSRS-ExtIEs F1AP-PROTOCOL-IES ::= {
	...
}


BAPAddress ::= BIT STRING (SIZE(10))

BAPCtrlPDUChannel ::= ENUMERATED {true, ...}

BAPlayerBHRLCchannelMappingInfo ::= SEQUENCE {
	bAPlayerBHRLCchannelMappingInfoToAdd			BAPlayerBHRLCchannelMappingInfoList			OPTIONAL,
	bAPlayerBHRLCchannelMappingInfoToRemove			MappingInformationtoRemove					OPTIONAL,
	iE-Extensions									ProtocolExtensionContainer { { BAPlayerBHRLCchannelMappingInfo-ExtIEs} } OPTIONAL,
	...
}

BAPlayerBHRLCchannelMappingInfo-ExtIEs F1AP-PROTOCOL-EXTENSION ::= {
	...
}

BAPlayerBHRLCchannelMappingInfoList ::= SEQUENCE (SIZE(1..maxnoofMappingEntries)) OF BAPlayerBHRLCchannelMappingInfo-Item

BAPlayerBHRLCchannelMappingInfo-Item ::= SEQUENCE {
	mappingInformationIndex			MappingInformationIndex,
	priorHopBAPAddress				BAPAddress		OPTIONAL,
	ingressbHRLCChannelID			BHRLCChannelID		OPTIONAL,
	nextHopBAPAddress				BAPAddress		OPTIONAL,
	egressbHRLCChannelID			BHRLCChannelID		OPTIONAL,
	iE-Extensions					ProtocolExtensionContainer { { BAPlayerBHRLCchannelMappingInfo-ItemExtIEs} } OPTIONAL,
	...
}

BAPlayerBHRLCchannelMappingInfo-ItemExtIEs F1AP-PROTOCOL-EXTENSION ::= {
	{ ID id-IngressNonF1terminatingTopologyIndicator	CRITICALITY ignore	EXTENSION IngressNonF1terminatingTopologyIndicator		PRESENCE optional}|
	{ ID id-EgressNonF1terminatingTopologyIndicator	CRITICALITY ignore	EXTENSION EgressNonF1terminatingTopologyIndicator		PRESENCE optional},
	...
}

BAPPathID ::= BIT STRING (SIZE(10))

BAPRoutingID ::= SEQUENCE {
	bAPAddress		BAPAddress,
	bAPPathID		BAPPathID,
	iE-Extensions	ProtocolExtensionContainer { { BAPRoutingIDExtIEs } }	OPTIONAL
}

BAPRoutingIDExtIEs	F1AP-PROTOCOL-EXTENSION ::= {
	...
}

BCBearerContextF1U-TNLInfo ::= CHOICE {
	locationindpendent				MBSF1UInformation,
	locationdependent				LocationDependentMBSF1UInformation,
	choice-extension	ProtocolIE-SingleContainer	{{BCBearerContextF1U-TNLInfo-ExtIEs}}
}

BCBearerContextF1U-TNLInfo-ExtIEs F1AP-PROTOCOL-IES ::= {
	...
}

BitRate ::= INTEGER (0..4000000000000,...)

BearerTypeChange ::= ENUMERATED {true, ...}

BHRLCChannelID ::= BIT STRING (SIZE(16))

BHChannels-FailedToBeModified-Item ::= SEQUENCE {
	bHRLCChannelID		BHRLCChannelID,
	cause		Cause		OPTIONAL,
	iE-Extensions	ProtocolExtensionContainer { { BHChannels-FailedToBeModified-ItemExtIEs } }	OPTIONAL
}

BHChannels-FailedToBeModified-ItemExtIEs	F1AP-PROTOCOL-EXTENSION ::= {
	...
}

BHChannels-FailedToBeSetup-Item ::= SEQUENCE {
	bHRLCChannelID		BHRLCChannelID,
	cause	Cause	OPTIONAL,
	iE-Extensions	ProtocolExtensionContainer { { BHChannels-FailedToBeSetup-ItemExtIEs } }	OPTIONAL
}

BHChannels-FailedToBeSetup-ItemExtIEs 	F1AP-PROTOCOL-EXTENSION ::= {
	...
}

BHChannels-FailedToBeSetupMod-Item ::= SEQUENCE {
	bHRLCChannelID		BHRLCChannelID,
	cause		Cause			OPTIONAL ,
	iE-Extensions	ProtocolExtensionContainer { { BHChannels-FailedToBeSetupMod-ItemExtIEs } }	OPTIONAL
}

BHChannels-FailedToBeSetupMod-ItemExtIEs	F1AP-PROTOCOL-EXTENSION ::= {
	...
}

BHChannels-Modified-Item ::= SEQUENCE {
	bHRLCChannelID			BHRLCChannelID,
	iE-Extensions	ProtocolExtensionContainer { { BHChannels-Modified-ItemExtIEs } }	OPTIONAL
}

BHChannels-Modified-ItemExtIEs	F1AP-PROTOCOL-EXTENSION ::= {
	...
}

BHChannels-Required-ToBeReleased-Item ::= SEQUENCE {
	bHRLCChannelID		BHRLCChannelID,
	iE-Extensions	ProtocolExtensionContainer { { BHChannels-Required-ToBeReleased-ItemExtIEs } }	OPTIONAL
}

BHChannels-Required-ToBeReleased-ItemExtIEs	F1AP-PROTOCOL-EXTENSION ::= {
	...
}

BHChannels-Setup-Item ::= SEQUENCE {
	bHRLCChannelID							BHRLCChannelID,
	iE-Extensions	ProtocolExtensionContainer { { BHChannels-Setup-ItemExtIEs } }	OPTIONAL
}

BHChannels-Setup-ItemExtIEs 	F1AP-PROTOCOL-EXTENSION ::= {
	...
}

BHChannels-SetupMod-Item ::= SEQUENCE {
	bHRLCChannelID							BHRLCChannelID,
	iE-Extensions	ProtocolExtensionContainer { { BHChannels-SetupMod-ItemExtIEs } }	OPTIONAL
}

BHChannels-SetupMod-ItemExtIEs 	F1AP-PROTOCOL-EXTENSION ::= {
	...
}

BHChannels-ToBeModified-Item ::= SEQUENCE {
	bHRLCChannelID					BHRLCChannelID,
	bHQoSInformation				BHQoSInformation,
	rLCmode				RLCMode	OPTIONAL,
	bAPCtrlPDUChannel	BAPCtrlPDUChannel		OPTIONAL,
	trafficMappingInfo	TrafficMappingInfo		OPTIONAL,
	iE-Extensions	ProtocolExtensionContainer { { BHChannels-ToBeModified-ItemExtIEs } }	OPTIONAL
}

BHChannels-ToBeModified-ItemExtIEs 	F1AP-PROTOCOL-EXTENSION ::= {
	...
}

BHChannels-ToBeReleased-Item ::= SEQUENCE {
	bHRLCChannelID		BHRLCChannelID,
	iE-Extensions	ProtocolExtensionContainer { { BHChannels-ToBeReleased-ItemExtIEs } }	OPTIONAL
}

BHChannels-ToBeReleased-ItemExtIEs 	F1AP-PROTOCOL-EXTENSION ::= {
	...
}

BHChannels-ToBeSetup-Item ::= SEQUENCE	{
	bHRLCChannelID						BHRLCChannelID,
	bHQoSInformation					BHQoSInformation,
	rLCmode								RLCMode,
	bAPCtrlPDUChannel					BAPCtrlPDUChannel		OPTIONAL,
	trafficMappingInfo					TrafficMappingInfo		OPTIONAL,
	iE-Extensions						ProtocolExtensionContainer { { BHChannels-ToBeSetup-ItemExtIEs } }	OPTIONAL
}

BHChannels-ToBeSetup-ItemExtIEs 	F1AP-PROTOCOL-EXTENSION ::= {
	...
}

BHChannels-ToBeSetupMod-Item ::= SEQUENCE {
	bHRLCChannelID				BHRLCChannelID,
	bHQoSInformation			BHQoSInformation,
	rLCmode				RLCMode,
	bAPCtrlPDUChannel	BAPCtrlPDUChannel		OPTIONAL,
	trafficMappingInfo	TrafficMappingInfo		OPTIONAL,
	iE-Extensions		ProtocolExtensionContainer { { BHChannels-ToBeSetupMod-ItemExtIEs } }	OPTIONAL
}

BHChannels-ToBeSetupMod-ItemExtIEs 	F1AP-PROTOCOL-EXTENSION ::= {
	...
}

BHInfo ::= SEQUENCE {
	bAProutingID			BAPRoutingID 	OPTIONAL,
	egressBHRLCCHList		EgressBHRLCCHList	OPTIONAL,
	iE-Extensions			ProtocolExtensionContainer { { BHInfo-ExtIEs} } OPTIONAL
}

BHInfo-ExtIEs F1AP-PROTOCOL-EXTENSION ::= {
	{ ID id-NonF1terminatingTopologyIndicator	CRITICALITY ignore	EXTENSION NonF1terminatingTopologyIndicator		PRESENCE optional	},
	...
}

BHQoSInformation ::= CHOICE {
	bHRLCCHQoS					QoSFlowLevelQoSParameters,
	eUTRANBHRLCCHQoS			EUTRANQoS,
	cPTrafficType				CPTrafficType,
	choice-extension			ProtocolIE-SingleContainer { { BHQoSInformation-ExtIEs} }
}

BHQoSInformation-ExtIEs F1AP-PROTOCOL-IES ::= {
	...
}

BHRLCCHList ::= SEQUENCE (SIZE(1..maxnoofBHRLCChannels)) OF BHRLCCHItem

BHRLCCHItem ::= SEQUENCE {
	bHRLCChannelID			BHRLCChannelID,
	iE-Extensions			ProtocolExtensionContainer {{BHRLCCHItemExtIEs }}	 OPTIONAL
}

BHRLCCHItemExtIEs F1AP-PROTOCOL-EXTENSION ::= {
	...
}

BH-Routing-Information-Added-List-Item ::= SEQUENCE {
	bAPRoutingID				BAPRoutingID,
	nextHopBAPAddress			BAPAddress,
	iE-Extensions				ProtocolExtensionContainer { { BH-Routing-Information-Added-List-ItemExtIEs} }	OPTIONAL
}

BH-Routing-Information-Added-List-ItemExtIEs F1AP-PROTOCOL-EXTENSION ::= {
	{ID id-NonF1terminatingTopologyIndicator  CRITICALITY ignore EXTENSION   NonF1terminatingTopologyIndicator		PRESENCE optional},
	...
}

BH-Routing-Information-Removed-List-Item ::= SEQUENCE {
	bAPRoutingID				BAPRoutingID,
	iE-Extensions				ProtocolExtensionContainer { { BH-Routing-Information-Removed-List-ItemExtIEs} }	OPTIONAL
}

BH-Routing-Information-Removed-List-ItemExtIEs F1AP-PROTOCOL-EXTENSION ::= {
	...
}

BPLMN-ID-Info-List ::= SEQUENCE (SIZE(1..maxnoofBPLMNsNR)) OF BPLMN-ID-Info-Item

BPLMN-ID-Info-Item ::= SEQUENCE {
	pLMN-Identity-List			AvailablePLMNList,
	extended-PLMN-Identity-List	ExtendedAvailablePLMN-List	OPTIONAL,
	fiveGS-TAC					FiveGS-TAC					OPTIONAL,
	nr-cell-ID					NRCellIdentity,
	ranac						RANAC						OPTIONAL,
	iE-Extensions				ProtocolExtensionContainer { { BPLMN-ID-Info-ItemExtIEs} } OPTIONAL,
	...
}

BPLMN-ID-Info-ItemExtIEs F1AP-PROTOCOL-EXTENSION ::= {
	{	ID id-ConfiguredTACIndication		CRITICALITY ignore	EXTENSION ConfiguredTACIndication		PRESENCE optional }|
	{	ID id-NPNBroadcastInformation		CRITICALITY reject EXTENSION NPNBroadcastInformation		PRESENCE optional},
	...
}

ServedPLMNs-List ::= SEQUENCE (SIZE(1..maxnoofBPLMNs)) OF ServedPLMNs-Item

ServedPLMNs-Item ::= SEQUENCE {
	pLMN-Identity				PLMN-Identity,
	iE-Extensions				ProtocolExtensionContainer { { ServedPLMNs-ItemExtIEs} } OPTIONAL,
	...
}

ServedPLMNs-ItemExtIEs F1AP-PROTOCOL-EXTENSION ::= {
{ ID id-TAISliceSupportList			CRITICALITY ignore	EXTENSION SliceSupportList				PRESENCE optional	}|
{ ID id-NPNSupportInfo				CRITICALITY reject	EXTENSION NPNSupportInfo				PRESENCE optional	}|
{ ID id-ExtendedTAISliceSupportList	CRITICALITY reject	EXTENSION ExtendedSliceSupportList		PRESENCE optional	}|
{ ID id-TAINSAGSupportList			CRITICALITY ignore	EXTENSION NSAGSupportList				PRESENCE optional},
	...
}

BroadcastCAGList ::= SEQUENCE (SIZE(1..maxnoofCAGsupported)) OF CAGID


BroadcastMRBs-FailedToBeModified-Item ::= SEQUENCE {
	mRB-ID						MRB-ID,
	cause						Cause							OPTIONAL,
	iE-Extensions				ProtocolExtensionContainer { { BroadcastMRBs-FailedtoBeModified-Item-ExtIEs} } OPTIONAL,
	...
}

BroadcastMRBs-FailedtoBeModified-Item-ExtIEs F1AP-PROTOCOL-EXTENSION ::= {
	...
}

BroadcastMRBs-FailedToBeSetup-Item ::= SEQUENCE {
	mRB-ID						MRB-ID,
	cause						Cause							OPTIONAL,
	iE-Extensions				ProtocolExtensionContainer { { BroadcastMRBs-FailedToBeSetup-Item-ExtIEs} } OPTIONAL,
	...
}

BroadcastMRBs-FailedToBeSetup-Item-ExtIEs F1AP-PROTOCOL-EXTENSION ::= {
	...
}

BroadcastMRBs-FailedToBeSetupMod-Item ::= SEQUENCE {
	mRB-ID						MRB-ID,
	cause						Cause							OPTIONAL,
	iE-Extensions				ProtocolExtensionContainer { { BroadcastMRBs-FailedToBeSetupMod-Item-ExtIEs} } OPTIONAL,
	...
}

BroadcastMRBs-FailedToBeSetupMod-Item-ExtIEs F1AP-PROTOCOL-EXTENSION ::= {
	...
}

BroadcastMRBs-Modified-Item ::= SEQUENCE {
	mRB-ID						MRB-ID,
	bcBearerCtxtF1U-TNLInfoatDU	BCBearerContextF1U-TNLInfo		OPTIONAL,
	iE-Extensions				ProtocolExtensionContainer { { BroadcastMRBs-Modified-Item-ExtIEs} } OPTIONAL,
	...
}

BroadcastMRBs-Modified-Item-ExtIEs F1AP-PROTOCOL-EXTENSION ::= {
	...
}

BroadcastMRBs-Setup-Item ::= SEQUENCE {
	mRB-ID						MRB-ID,
	bcBearerCtxtF1U-TNLInfoatDU	BCBearerContextF1U-TNLInfo,
	iE-Extensions				ProtocolExtensionContainer { { BroadcastMRBs-Setup-Item-ExtIEs} } OPTIONAL,
	...
}

BroadcastMRBs-Setup-Item-ExtIEs F1AP-PROTOCOL-EXTENSION ::= {
	...
}

BroadcastMRBs-SetupMod-Item ::= SEQUENCE {
	mRB-ID						MRB-ID,
	bcBearerCtxtF1U-TNLInfoatDU	BCBearerContextF1U-TNLInfo,
	iE-Extensions				ProtocolExtensionContainer { { BroadcastMRBs-SetupMod-Item-ExtIEs} } OPTIONAL,
	...
}

BroadcastMRBs-SetupMod-Item-ExtIEs F1AP-PROTOCOL-EXTENSION ::= {
	...
}

BroadcastMRBs-ToBeModified-Item ::= SEQUENCE {
	mRB-ID							MRB-ID,
	mRB-QoSInformation				QoSFlowLevelQoSParameters		OPTIONAL,
	mBS-Flows-Mapped-To-MRB-List	MBS-Flows-Mapped-To-MRB-List	OPTIONAL,
	bcBearerCtxtF1U-TNLInfoatCU		BCBearerContextF1U-TNLInfo		OPTIONAL,
	iE-Extensions					ProtocolExtensionContainer { { BroadcastMRBs-ToBeModified-Item-ExtIEs} } OPTIONAL,
	...
}

BroadcastMRBs-ToBeModified-Item-ExtIEs F1AP-PROTOCOL-EXTENSION ::= {
	...
}

BroadcastMRBs-ToBeReleased-Item	::= SEQUENCE {
	mRB-ID						MRB-ID,
	iE-Extensions				ProtocolExtensionContainer { { BroadcastMRBs-ToBeReleased-ItemExtIEs } }	OPTIONAL,
	...
}

BroadcastMRBs-ToBeReleased-ItemExtIEs 	F1AP-PROTOCOL-EXTENSION ::= {
	...
}

BroadcastMRBs-ToBeSetup-Item ::= SEQUENCE {
	mRB-ID							MRB-ID,
	mRB-QoSInformation				QoSFlowLevelQoSParameters,
	mBS-Flows-Mapped-To-MRB-List	MBS-Flows-Mapped-To-MRB-List,
	bcBearerCtxtF1U-TNLInfoatCU		BCBearerContextF1U-TNLInfo	,
	iE-Extensions					ProtocolExtensionContainer { { BroadcastMRBs-ToBeSetup-Item-ExtIEs} },
	...
}

BroadcastMRBs-ToBeSetup-Item-ExtIEs F1AP-PROTOCOL-EXTENSION ::= {
	...
}

BroadcastMRBs-ToBeSetupMod-Item ::= SEQUENCE {
	mRB-ID							MRB-ID,
	mRB-QoSInformation				QoSFlowLevelQoSParameters,
	mBS-Flows-Mapped-To-MRB-List	MBS-Flows-Mapped-To-MRB-List,
	bcBearerCtxtF1U-TNLInfoatCU		BCBearerContextF1U-TNLInfo,
	iE-Extensions					ProtocolExtensionContainer { { BroadcastMRBs-ToBeSetupMod-Item-ExtIEs} },
	...
}

BroadcastMRBs-ToBeSetupMod-Item-ExtIEs F1AP-PROTOCOL-EXTENSION ::= {
	...
}


BroadcastNIDList ::= SEQUENCE (SIZE(1..maxnoofNIDsupported)) OF NID

BroadcastSNPN-ID-List ::= SEQUENCE (SIZE(1..maxnoofNIDsupported)) OF BroadcastSNPN-ID-List-Item

BroadcastSNPN-ID-List-Item ::= SEQUENCE {
	pLMN-Identity				PLMN-Identity,
	broadcastNIDList			BroadcastNIDList,
	iE-Extensions				ProtocolExtensionContainer { { BroadcastSNPN-ID-List-ItemExtIEs} } OPTIONAL,
	...
}

BroadcastSNPN-ID-List-ItemExtIEs F1AP-PROTOCOL-EXTENSION ::= {
	...
}

BroadcastPNI-NPN-ID-List ::= SEQUENCE (SIZE(1..maxnoofCAGsupported)) OF BroadcastPNI-NPN-ID-List-Item

BroadcastPNI-NPN-ID-List-Item ::= SEQUENCE {
	pLMN-Identity				PLMN-Identity,
	broadcastCAGList			BroadcastCAGList,
	iE-Extensions				ProtocolExtensionContainer { { BroadcastPNI-NPN-ID-List-ItemExtIEs} } OPTIONAL,
	...
}

BroadcastPNI-NPN-ID-List-ItemExtIEs F1AP-PROTOCOL-EXTENSION ::= {
	...
}

BroadcastAreaScope ::= CHOICE {
	completeSuccess			NULL,
	partialSuccess			PartialSuccessCell,
	choice-extension		ProtocolIE-SingleContainer { { BroadcastAreaScope-ExtIEs } }
}

BroadcastAreaScope-ExtIEs F1AP-PROTOCOL-IES::={
	...
}

BroadcastCellList ::= SEQUENCE (SIZE(1.. maxCellingNBDU)) OF Broadcast-Cell-List-Item
Broadcast-Cell-List-Item ::= SEQUENCE {
	cellID				NRCGI,
	iE-Extensions				ProtocolExtensionContainer { { Broadcast-Cell-List-ItemExtIEs} } OPTIONAL,
	...
}

Broadcast-Cell-List-ItemExtIEs F1AP-PROTOCOL-EXTENSION ::= {
	...
}

BufferSizeThresh ::= INTEGER(0..16777215)

BurstArrivalTime ::= OCTET STRING

-- C
CAGID ::= BIT STRING (SIZE(32))

Cancel-all-Warning-Messages-Indicator ::= ENUMERATED {true, ...}

Candidate-SpCell-Item ::= SEQUENCE {
	candidate-SpCell-ID			NRCGI	,
	iE-Extensions	ProtocolExtensionContainer { { Candidate-SpCell-ItemExtIEs } }	OPTIONAL,
	...
}

Candidate-SpCell-ItemExtIEs 	F1AP-PROTOCOL-EXTENSION ::= {
	...
}

CapacityValue::= SEQUENCE {
	capacityValue				INTEGER (0..100),
	sSBAreaCapacityValueList	SSBAreaCapacityValueList		OPTIONAL,
	iE-Extensions				ProtocolExtensionContainer { { CapacityValue-ExtIEs} } OPTIONAL
}

CapacityValue-ExtIEs 	F1AP-PROTOCOL-EXTENSION ::= {
	...
}

Cause ::= CHOICE {
	radioNetwork		CauseRadioNetwork,
	transport			CauseTransport,
	protocol			CauseProtocol,
	misc				CauseMisc,
	choice-extension	ProtocolIE-SingleContainer { { Cause-ExtIEs} }
}

Cause-ExtIEs F1AP-PROTOCOL-IES ::= {
	...
}

CauseMisc ::= ENUMERATED {
	control-processing-overload,
	not-enough-user-plane-processing-resources,
	hardware-failure,
	om-intervention,
	unspecified,
	...
}

CauseProtocol ::= ENUMERATED {
	transfer-syntax-error,
	abstract-syntax-error-reject,
	abstract-syntax-error-ignore-and-notify,
	message-not-compatible-with-receiver-state,
	semantic-error,
	abstract-syntax-error-falsely-constructed-message,
	unspecified,
	...
}

CauseRadioNetwork ::= ENUMERATED {
	unspecified,
	rl-failure-rlc,
	unknown-or-already-allocated-gnb-cu-ue-f1ap-id,
	unknown-or-already-allocated-gnb-du-ue-f1ap-id,
	unknown-or-inconsistent-pair-of-ue-f1ap-id,
	interaction-with-other-procedure,
	not-supported-qci-Value,
	action-desirable-for-radio-reasons,
	no-radio-resources-available,
	procedure-cancelled,
	normal-release,
	...,
	cell-not-available,
	rl-failure-others,
	ue-rejection,
	resources-not-available-for-the-slice,
	amf-initiated-abnormal-release,
	release-due-to-pre-emption,
	plmn-not-served-by-the-gNB-CU,
	multiple-drb-id-instances,
	unknown-drb-id,
	multiple-bh-rlc-ch-id-instances,
	unknown-bh-rlc-ch-id,
	cho-cpc-resources-tobechanged,
	nPN-not-supported,
	nPN-access-denied,
	gNB-CU-Cell-Capacity-Exceeded,
	report-characteristics-empty,
	existing-measurement-ID,
	measurement-temporarily-not-available,
	measurement-not-supported-for-the-object,
	unknown-bh-address,
	unknown-bap-routing-id,
	insufficient-ue-capabilities,
	scg-activation-deactivation-failure,
	scg-deactivation-failure-due-to-data-transmission,
	requested-item-not-supported-on-time,
	unknown-or-already-allocated-gNB-CU-MBS-F1AP-ID,
	unknown-or-already-allocated-gNB-DU-MBS-F1AP-ID,
	unknown-or-inconsistent-pair-of-MBS-F1AP-ID,
	unknown-or-inconsistent-MRB-ID,
	tat-sdt-expiry

}

CauseTransport ::= ENUMERATED {
	unspecified,
	transport-resource-unavailable,
	...,
	unknown-TNL-address-for-IAB,
	unknown-UP-TNL-information-for-IAB
}

CellGroupConfig ::= OCTET STRING

CellCapacityClassValue ::= INTEGER (1..100,...)

Cell-Direction ::= ENUMERATED {dl-only, ul-only}

CellMeasurementResultList ::= SEQUENCE (SIZE(1.. maxCellingNBDU)) OF CellMeasurementResultItem

CellMeasurementResultItem ::= SEQUENCE {
	cellID							NRCGI,
	radioResourceStatus				RadioResourceStatus 			OPTIONAL,
	compositeAvailableCapacityGroup	CompositeAvailableCapacityGroup	OPTIONAL,
	sliceAvailableCapacity			SliceAvailableCapacity 			OPTIONAL,
	numberofActiveUEs 				NumberofActiveUEs				OPTIONAL,
	iE-Extensions					ProtocolExtensionContainer { { CellMeasurementResultItem-ExtIEs} } OPTIONAL
}

CellMeasurementResultItem-ExtIEs 	F1AP-PROTOCOL-EXTENSION ::= {
	{ ID id-NR-U-Channel-List	CRITICALITY ignore	EXTENSION NR-U-Channel-List PRESENCE optional },
	...
}

Cell-Portion-ID ::= INTEGER (0..4095,...)

CellsForSON-List ::= SEQUENCE (SIZE(1.. maxServedCellforSON)) OF CellsForSON-Item

CellsForSON-Item ::= SEQUENCE {
	nRCGI											NRCGI,
	neighbourNR-CellsForSON-List					NeighbourNR-CellsForSON-List									OPTIONAL,
	iE-Extensions									ProtocolExtensionContainer { { CellsForSON-Item-ExtIEs} }	OPTIONAL,
	...
}

CellsForSON-Item-ExtIEs F1AP-PROTOCOL-EXTENSION ::= {
	...
}

Cells-Failed-to-be-Activated-List-Item ::= SEQUENCE {
	nRCGI				NRCGI,
	cause				Cause,
	iE-Extensions		ProtocolExtensionContainer { { Cells-Failed-to-be-Activated-List-ItemExtIEs } }	OPTIONAL,
	...
}

Cells-Failed-to-be-Activated-List-ItemExtIEs 	F1AP-PROTOCOL-EXTENSION ::= {
	...
}

Cells-Status-Item ::= SEQUENCE {
	nRCGI			NRCGI,
	service-status		Service-Status,
	iE-Extensions				ProtocolExtensionContainer { { Cells-Status-ItemExtIEs } }	OPTIONAL,
	...
}

Cells-Status-ItemExtIEs 	F1AP-PROTOCOL-EXTENSION ::= {
	...
}

Cells-To-Be-Broadcast-Item ::= SEQUENCE {
	nRCGI				NRCGI,
	iE-Extensions		ProtocolExtensionContainer { { Cells-To-Be-Broadcast-ItemExtIEs } }	OPTIONAL,
	...
}

Cells-To-Be-Broadcast-ItemExtIEs 	F1AP-PROTOCOL-EXTENSION ::= {
	...
}

Cells-Broadcast-Completed-Item ::= SEQUENCE {
	nRCGI				NRCGI,
	iE-Extensions		ProtocolExtensionContainer { { Cells-Broadcast-Completed-ItemExtIEs } }	OPTIONAL,
	...
}

Cells-Broadcast-Completed-ItemExtIEs 	F1AP-PROTOCOL-EXTENSION ::= {
	...
}

Broadcast-To-Be-Cancelled-Item ::= SEQUENCE {
	nRCGI				NRCGI,
	iE-Extensions		ProtocolExtensionContainer { { Broadcast-To-Be-Cancelled-ItemExtIEs } }	OPTIONAL,
	...
}

Broadcast-To-Be-Cancelled-ItemExtIEs 	F1AP-PROTOCOL-EXTENSION ::= {
	...
}


Cells-Broadcast-Cancelled-Item ::= SEQUENCE {
	nRCGI				NRCGI,
	numberOfBroadcasts	NumberOfBroadcasts,
	iE-Extensions		ProtocolExtensionContainer { { Cells-Broadcast-Cancelled-ItemExtIEs } }	OPTIONAL,
	...
}

Cells-Broadcast-Cancelled-ItemExtIEs 	F1AP-PROTOCOL-EXTENSION ::= {
	...
}

Cells-to-be-Activated-List-Item ::= SEQUENCE {
	nRCGI		NRCGI,
	nRPCI		NRPCI		OPTIONAL,
	iE-Extensions				ProtocolExtensionContainer { { Cells-to-be-Activated-List-ItemExtIEs} }	OPTIONAL,
	...
}

Cells-to-be-Activated-List-ItemExtIEs 	F1AP-PROTOCOL-EXTENSION ::= {
	{ ID id-gNB-CUSystemInformation			CRITICALITY reject	EXTENSION GNB-CUSystemInformation				PRESENCE optional }|
	{ ID id-AvailablePLMNList				CRITICALITY ignore	EXTENSION AvailablePLMNList						PRESENCE optional }|
	{ ID id-ExtendedAvailablePLMN-List		CRITICALITY ignore	EXTENSION ExtendedAvailablePLMN-List			PRESENCE optional }|
	{ ID id-IAB-Info-IAB-donor-CU			CRITICALITY ignore	EXTENSION IAB-Info-IAB-donor-CU					PRESENCE optional}|
	{ ID id-AvailableSNPN-ID-List			CRITICALITY ignore	EXTENSION AvailableSNPN-ID-List					PRESENCE optional }|
	{ ID id-MBS-Broadcast-NeighbourCellList	CRITICALITY ignore	EXTENSION MBS-Broadcast-NeighbourCellList	PRESENCE optional },
	...
}

Cells-to-be-Deactivated-List-Item ::= SEQUENCE {
	nRCGI			NRCGI	,
	iE-Extensions				ProtocolExtensionContainer { { Cells-to-be-Deactivated-List-ItemExtIEs } }	OPTIONAL,
	...
}

Cells-to-be-Deactivated-List-ItemExtIEs 	F1AP-PROTOCOL-EXTENSION ::= {
	...
}

Cells-to-be-Barred-Item::= SEQUENCE {
	nRCGI			NRCGI	,
	cellBarred		CellBarred,
	iE-Extensions				ProtocolExtensionContainer { { Cells-to-be-Barred-Item-ExtIEs } }	OPTIONAL
}

Cells-to-be-Barred-Item-ExtIEs 	F1AP-PROTOCOL-EXTENSION ::= {
	{ ID id-IAB-Barred	CRITICALITY ignore	EXTENSION IAB-Barred		PRESENCE optional },

	...
}


CellBarred	::=	ENUMERATED {barred, not-barred, ...}

CellSize ::= ENUMERATED {verysmall, small, medium, large, ...}

CellToReportList ::= SEQUENCE (SIZE(1.. maxCellingNBDU)) OF CellToReportItem

CellToReportItem ::= SEQUENCE {
	cellID		NRCGI,
	sSBToReportList		SSBToReportList		 OPTIONAL,
	sliceToReportList	SliceToReportList	 OPTIONAL,
	iE-Extensions	ProtocolExtensionContainer { { CellToReportItem-ExtIEs} } OPTIONAL
}

CellToReportItem-ExtIEs 	F1AP-PROTOCOL-EXTENSION ::= {
	...
}

CellType ::= SEQUENCE {
	cellSize		CellSize,
	iE-Extensions		ProtocolExtensionContainer { {CellType-ExtIEs} }	OPTIONAL,
	...
}

CellType-ExtIEs F1AP-PROTOCOL-EXTENSION ::= {
	...
}

CellULConfigured ::=  ENUMERATED {none, ul, sul, ul-and-sul, ...}

CG-SDTQueryIndication ::=  ENUMERATED {true, ...}

CG-SDTKeptIndicator ::= ENUMERATED {true, ...}

CG-SDTindicatorSetup ::= ENUMERATED {true, ...}

CG-SDTindicatorMod ::= ENUMERATED {true, false, ...}

CG-SDTSessionInfo ::= SEQUENCE {
	gNB-CU-UE-F1AP-ID					GNB-CU-UE-F1AP-ID,
	gNB-DU-UE-F1AP-ID					GNB-DU-UE-F1AP-ID,
	iE-Extensions						ProtocolExtensionContainer {{CG-SDTSessionInfo-ExtIEs}}		OPTIONAL,
	...
}


CG-SDTSessionInfo-ExtIEs	F1AP-PROTOCOL-EXTENSION ::= {
	...
}

ChannelOccupancyTimePercentage ::= INTEGER (0..100,...)

Child-IAB-Nodes-NA-Resource-List ::= SEQUENCE (SIZE(1..maxnoofChildIABNodes)) OF Child-IAB-Nodes-NA-Resource-List-Item

Child-IAB-Nodes-NA-Resource-List-Item::= SEQUENCE {
	gNB-CU-UE-F1AP-ID	GNB-CU-UE-F1AP-ID,
	gNB-DU-UE-F1AP-ID	GNB-DU-UE-F1AP-ID,
	nA-Resource-Configuration-List		NA-Resource-Configuration-List 		OPTIONAL,
	iE-Extensions		ProtocolExtensionContainer { { Child-IAB-Nodes-NA-Resource-List-Item-ExtIEs} } OPTIONAL
}

Child-IAB-Nodes-NA-Resource-List-Item-ExtIEs F1AP-PROTOCOL-EXTENSION ::= {
	...
}


Child-Node-Cells-List ::= SEQUENCE (SIZE(1..maxnoofChildIABNodes)) OF Child-Node-Cells-List-Item

Child-Node-Cells-List-Item ::=	SEQUENCE{
	nRCGI 								NRCGI,
	iAB-DU-Cell-Resource-Configuration-Mode-Info 	IAB-DU-Cell-Resource-Configuration-Mode-Info	OPTIONAL,
	iAB-STC-Info						IAB-STC-Info			OPTIONAL,
	rACH-Config-Common					RACH-Config-Common		OPTIONAL,
	rACH-Config-Common-IAB				RACH-Config-Common-IAB	OPTIONAL,
	cSI-RS-Configuration				OCTET STRING			OPTIONAL,
	sR-Configuration					OCTET STRING			OPTIONAL,
	pDCCH-ConfigSIB1					OCTET STRING			OPTIONAL,
	sCS-Common							OCTET STRING	OPTIONAL,
	multiplexingInfo					MultiplexingInfo	OPTIONAL,
	iE-Extensions						ProtocolExtensionContainer {{Child-Node-Cells-List-Item-ExtIEs}}		OPTIONAL
}

Child-Node-Cells-List-Item-ExtIEs 	F1AP-PROTOCOL-EXTENSION ::= {
	...
}

Child-Nodes-List ::= SEQUENCE (SIZE(1..maxnoofChildIABNodes)) OF Child-Nodes-List-Item

Child-Nodes-List-Item ::= SEQUENCE{
	gNB-CU-UE-F1AP-ID	GNB-CU-UE-F1AP-ID,
	gNB-DU-UE-F1AP-ID	GNB-DU-UE-F1AP-ID,
	child-Node-Cells-List 	Child-Node-Cells-List	OPTIONAL,
	iE-Extensions			ProtocolExtensionContainer {{Child-Nodes-List-Item-ExtIEs}}		OPTIONAL
}

Child-Nodes-List-Item-ExtIEs 	F1AP-PROTOCOL-EXTENSION ::= {
	...
}

CHOtrigger-InterDU ::= ENUMERATED {
	cho-initiation,
	cho-replace,
	...
}

CHOtrigger-IntraDU ::= ENUMERATED {
	cho-initiation,
	cho-replace,
	cho-cancel,
	...
}

CNSubgroupID ::= INTEGER (0..7, ...)

CNUEPagingIdentity ::= CHOICE {
	fiveG-S-TMSI			BIT STRING (SIZE(48)),
	choice-extension			ProtocolIE-SingleContainer { { CNUEPagingIdentity-ExtIEs } }
}

CNUEPagingIdentity-ExtIEs F1AP-PROTOCOL-IES ::= {
	...
}

CompositeAvailableCapacityGroup ::= SEQUENCE {
	compositeAvailableCapacityDownlink	CompositeAvailableCapacity,
	compositeAvailableCapacityUplink 	CompositeAvailableCapacity,
	iE-Extensions	ProtocolExtensionContainer { { CompositeAvailableCapacityGroup-ExtIEs} } OPTIONAL
}

CompositeAvailableCapacityGroup-ExtIEs 	F1AP-PROTOCOL-EXTENSION ::= {
	{ ID id-CompositeAvailableCapacity-SUL		CRITICALITY ignore	EXTENSION CompositeAvailableCapacity		PRESENCE optional	},
	...
}

CompositeAvailableCapacity ::= SEQUENCE {
	cellCapacityClassValue 	CellCapacityClassValue		OPTIONAL,
	capacityValue			CapacityValue,
	iE-Extensions	ProtocolExtensionContainer { { CompositeAvailableCapacity-ExtIEs} } OPTIONAL
}

CompositeAvailableCapacity-ExtIEs 	F1AP-PROTOCOL-EXTENSION ::= {
	...
}

CHO-Probability ::= INTEGER (1..100)

ConditionalInterDUMobilityInformation ::= SEQUENCE {
	cho-trigger						CHOtrigger-InterDU,
	targetgNB-DUUEF1APID			GNB-DU-UE-F1AP-ID							OPTIONAL
		-- This IE shall be present if the cho-trigger IE is present and set to "cho-replace" --,
	iE-Extensions					ProtocolExtensionContainer { { ConditionalInterDUMobilityInformation-ExtIEs} }	OPTIONAL,
	...
}

ConditionalInterDUMobilityInformation-ExtIEs F1AP-PROTOCOL-EXTENSION ::={
	{ ID id-EstimatedArrivalProbability		CRITICALITY ignore		EXTENSION CHO-Probability		PRESENCE optional	},
	...
}

ConditionalIntraDUMobilityInformation ::= SEQUENCE {
	cho-trigger						CHOtrigger-IntraDU,
	targetCellsTocancel				TargetCellList								OPTIONAL,
	-- This IE may be present if the cho-trigger IE is present and set to "cho-cancel"
	iE-Extensions					ProtocolExtensionContainer { { ConditionalIntraDUMobilityInformation-ExtIEs} }	OPTIONAL,
	...
}

ConditionalIntraDUMobilityInformation-ExtIEs F1AP-PROTOCOL-EXTENSION ::={
	{ ID id-EstimatedArrivalProbability		CRITICALITY ignore		EXTENSION CHO-Probability		PRESENCE optional	},
	...
}

ConfigRestrictInfoDAPS ::= OCTET STRING

ConfiguredTACIndication ::= ENUMERATED {
	true,
	...
}


CoordinateID ::= INTEGER (0..511, ...)

Coverage-Modification-Notification ::= SEQUENCE {
	coverage-Modification-List				Coverage-Modification-List,
	iE-Extensions								ProtocolExtensionContainer { { Coverage-Modification-Notification-ExtIEs} }	OPTIONAL,
	...
}

Coverage-Modification-Notification-ExtIEs F1AP-PROTOCOL-EXTENSION ::={
	...
}

Coverage-Modification-List ::= SEQUENCE (SIZE (1..maxCellingNBDU)) OF Coverage-Modification-Item

Coverage-Modification-Item ::= SEQUENCE {
	nRCGI								NRCGI,
	cellCoverageState					CellCoverageState,
	sSBCoverageModificationList			SSBCoverageModification-List OPTIONAL,
	iE-Extension			ProtocolExtensionContainer { { Coverage-Modification-Item-ExtIEs} } 				OPTIONAL,
	...
}

Coverage-Modification-Item-ExtIEs F1AP-PROTOCOL-EXTENSION ::= {
	...
}

CellCoverageState ::= INTEGER (0..63, ...)


CCO-Assistance-Information ::= SEQUENCE {
	cCO-issue-detection				CCO-issue-detection		OPTIONAL,
	affectedCellsAndBeams-List		AffectedCellsAndBeams-List 		OPTIONAL,
	iE-Extensions					ProtocolExtensionContainer { { CCO-Assistance-Information-ExtIEs} }	OPTIONAL,
	...
}

CCO-Assistance-Information-ExtIEs F1AP-PROTOCOL-EXTENSION ::={
	...
}


CCO-issue-detection	::=	ENUMERATED {
	coverage,
	cell-edge-capacity,
	...}


CP-TransportLayerAddress ::= CHOICE {
	endpoint-IP-address				TransportLayerAddress,
	endpoint-IP-address-and-port	Endpoint-IP-address-and-port,
	choice-extension				ProtocolIE-SingleContainer { { CP-TransportLayerAddress-ExtIEs } }
}

CP-TransportLayerAddress-ExtIEs F1AP-PROTOCOL-IES ::= {
	...
}

CPACMCGInformation ::= SEQUENCE {
	cpac-trigger					CPAC-trigger,
	pscellid						NRCGI,
	iE-Extensions					ProtocolExtensionContainer { { CPACMCGInformation-ExtIEs} }	OPTIONAL,
	...
}

CPACMCGInformation-ExtIEs F1AP-PROTOCOL-EXTENSION ::= {
	...
}

CPAC-trigger ::= ENUMERATED {
	cpac-preparation,
	cpac-executed,
	...
}

CPTrafficType ::= INTEGER (1..3,...)

CriticalityDiagnostics ::= SEQUENCE {
	procedureCode					ProcedureCode														OPTIONAL,
	triggeringMessage				TriggeringMessage													OPTIONAL,
	procedureCriticality			Criticality															OPTIONAL,
	transactionID					TransactionID														OPTIONAL,
	iEsCriticalityDiagnostics		CriticalityDiagnostics-IE-List										OPTIONAL,
	iE-Extensions					ProtocolExtensionContainer {{CriticalityDiagnostics-ExtIEs}}		OPTIONAL,
	...
}

CriticalityDiagnostics-ExtIEs F1AP-PROTOCOL-EXTENSION ::= {
	...
}

CriticalityDiagnostics-IE-List ::= SEQUENCE (SIZE (1.. maxnoofErrors)) OF CriticalityDiagnostics-IE-Item

CriticalityDiagnostics-IE-Item ::= SEQUENCE {
	iECriticality			Criticality,
	iE-ID					ProtocolIE-ID,
	typeOfError 			TypeOfError,
	iE-Extensions			ProtocolExtensionContainer {{CriticalityDiagnostics-IE-Item-ExtIEs}}	OPTIONAL,
	...
}

CriticalityDiagnostics-IE-Item-ExtIEs F1AP-PROTOCOL-EXTENSION ::= {
	...
}

C-RNTI ::= INTEGER (0..65535, ...)

CUDURadioInformationType ::= CHOICE {
	rIM								CUDURIMInformation,
	choice-extension				ProtocolIE-SingleContainer { { CUDURadioInformationType-ExtIEs} }
}

CUDURadioInformationType-ExtIEs F1AP-PROTOCOL-IES ::= {
	...
}

CUDURIMInformation ::= SEQUENCE {
	victimgNBSetID			GNBSetID,
	rIMRSDetectionStatus	RIMRSDetectionStatus,
	iE-Extensions			ProtocolExtensionContainer { { CUDURIMInformation-ExtIEs} }	OPTIONAL
}

CUDURIMInformation-ExtIEs F1AP-PROTOCOL-EXTENSION ::= {
	...
}

CUtoDURRCInformation ::= SEQUENCE {
	cG-ConfigInfo						CG-ConfigInfo						OPTIONAL,
	uE-CapabilityRAT-ContainerList		UE-CapabilityRAT-ContainerList		OPTIONAL,
	measConfig							MeasConfig							OPTIONAL,
	iE-Extensions				ProtocolExtensionContainer { { CUtoDURRCInformation-ExtIEs} } OPTIONAL,
	...
}

CUtoDURRCInformation-ExtIEs F1AP-PROTOCOL-EXTENSION ::= {
	{ ID id-HandoverPreparationInformation	CRITICALITY ignore	EXTENSION HandoverPreparationInformation		PRESENCE optional }|
	{ ID id-CellGroupConfig					CRITICALITY ignore	EXTENSION CellGroupConfig							PRESENCE optional }|
	{ ID id-MeasurementTimingConfiguration	CRITICALITY ignore	EXTENSION MeasurementTimingConfiguration		PRESENCE optional }|
	{ ID id-UEAssistanceInformation			CRITICALITY ignore	EXTENSION UEAssistanceInformation					PRESENCE optional }|
	{ ID id-CG-Config						CRITICALITY ignore	EXTENSION CG-Config									PRESENCE optional }|
	{ ID id-UEAssistanceInformationEUTRA	CRITICALITY ignore	EXTENSION UEAssistanceInformationEUTRA			PRESENCE optional }|
	{ ID id-LocationMeasurementInformation	CRITICALITY ignore	EXTENSION LocationMeasurementInformation		PRESENCE optional }|
	{ ID id-MUSIM-GapConfig					CRITICALITY reject	EXTENSION MUSIM-GapConfig							PRESENCE optional }|
	{ ID id-SDT-MAC-PHY-CG-Config			CRITICALITY ignore	EXTENSION SDT-MAC-PHY-CG-Config						PRESENCE optional }|
	{ ID id-MBSInterestIndication			CRITICALITY ignore	EXTENSION MBSInterestIndication						PRESENCE optional }|
	{ ID id-NeedForGapsInfoNR				CRITICALITY ignore	EXTENSION NeedForGapsInfoNR							PRESENCE optional }|
	{ ID id-NeedForGapNCSGInfoNR			CRITICALITY ignore	EXTENSION NeedForGapNCSGInfoNR						PRESENCE optional }|
	{ ID id-NeedForGapNCSGInfoEUTRA			CRITICALITY ignore	EXTENSION NeedForGapNCSGInfoEUTRA					PRESENCE optional }|
	{ ID id-ConfigRestrictInfoDAPS			CRITICALITY ignore	EXTENSION ConfigRestrictInfoDAPS					PRESENCE optional },
	...
}

-- D

DAPS-HO-Status::= ENUMERATED{initiation,... }

DCBasedDuplicationConfigured::= ENUMERATED{true,..., false}

Dedicated-SIDelivery-NeededUE-Item ::= SEQUENCE {
	gNB-CU-UE-F1AP-ID						GNB-CU-UE-F1AP-ID,
	nRCGI									NRCGI,
	iE-Extensions							ProtocolExtensionContainer { { DedicatedSIDeliveryNeededUE-Item-ExtIEs} } OPTIONAL,
	...
}

DedicatedSIDeliveryNeededUE-Item-ExtIEs F1AP-PROTOCOL-EXTENSION::={
	...
}


DL-PRS ::= SEQUENCE {
	prsid 					INTEGER (0..255),
	dl-PRSResourceSetID		PRS-Resource-Set-ID,
	dl-PRSResourceID		PRS-Resource-ID	OPTIONAL,
	iE-Extensions			ProtocolExtensionContainer { {DL-PRS-ExtIEs} }	OPTIONAL
}

DL-PRS-ExtIEs F1AP-PROTOCOL-EXTENSION ::= {
	...
}

DL-PRSMutingPattern ::= CHOICE {
	two					BIT STRING (SIZE(2)),
	four				BIT STRING (SIZE(4)),
	six					BIT STRING (SIZE(6)),
	eight				BIT STRING (SIZE(8)),
	sixteen				BIT STRING (SIZE(16)),
	thirty-two			BIT STRING (SIZE(32)),
	choice-extension							ProtocolIE-SingleContainer { { DL-PRSMutingPattern-ExtIEs } }
}

DL-PRSMutingPattern-ExtIEs F1AP-PROTOCOL-IES ::= {
	...
}

DLPRSResourceCoordinates ::= SEQUENCE {
	listofDL-PRSResourceSetARP		SEQUENCE (SIZE(1.. maxnoofPRS-ResourceSets)) OF DLPRSResourceSetARP,
	iE-Extensions					ProtocolExtensionContainer { { DLPRSResourceCoordinates-ExtIEs } } OPTIONAL
}

DLPRSResourceCoordinates-ExtIEs F1AP-PROTOCOL-EXTENSION ::= {
	...
}

DLPRSResourceSetARP ::= SEQUENCE {
	dl-PRSResourceSetID				PRS-Resource-Set-ID,
	dL-PRSResourceSetARPLocation	DL-PRSResourceSetARPLocation,
	listofDL-PRSResourceARP			SEQUENCE (SIZE(1.. maxnoofPRS-ResourcesPerSet)) OF DLPRSResourceARP,
	iE-Extensions					ProtocolExtensionContainer { { DLPRSResourceSetARP-ExtIEs } } OPTIONAL
}

DLPRSResourceSetARP-ExtIEs F1AP-PROTOCOL-EXTENSION ::= {
	...
}


DL-PRSResourceSetARPLocation ::= CHOICE {
	relativeGeodeticLocation			RelativeGeodeticLocation,
	relativeCartesianLocation			RelativeCartesianLocation,
	choice-Extension					ProtocolIE-SingleContainer { { DL-PRSResourceSetARPLocation-ExtIEs } }
}

DL-PRSResourceSetARPLocation-ExtIEs F1AP-PROTOCOL-IES ::= {
	...
}


DLPRSResourceARP ::= SEQUENCE {
	dl-PRSResourceID			PRS-Resource-ID,
	dL-PRSResourceARPLocation	DL-PRSResourceARPLocation,
	iE-Extensions				ProtocolExtensionContainer { { DLPRSResourceARP-ExtIEs } } OPTIONAL
}

DLPRSResourceARP-ExtIEs F1AP-PROTOCOL-EXTENSION ::= {
	...
}

DL-PRSResourceARPLocation ::= CHOICE {
	relativeGeodeticLocation			RelativeGeodeticLocation,
	relativeCartesianLocation			RelativeCartesianLocation,
	choice-Extension					ProtocolIE-SingleContainer { { DL-PRSResourceARPLocation-ExtIEs } }
}

DL-PRSResourceARPLocation-ExtIEs F1AP-PROTOCOL-IES ::= {
	...
}

DL-UP-TNL-Address-to-Update-List-Item	::= SEQUENCE {
	oldIPAdress						TransportLayerAddress,
	newIPAdress						TransportLayerAddress,
	iE-Extensions	ProtocolExtensionContainer { { DL-UP-TNL-Address-to-Update-List-ItemExtIEs } }	OPTIONAL,
	...
}

DL-UP-TNL-Address-to-Update-List-ItemExtIEs 	F1AP-PROTOCOL-EXTENSION ::= {
	...
}

DLUPTNLInformation-ToBeSetup-List ::= SEQUENCE (SIZE(1..maxnoofDLUPTNLInformation)) OF DLUPTNLInformation-ToBeSetup-Item

DLUPTNLInformation-ToBeSetup-Item ::= SEQUENCE {
	dLUPTNLInformation	UPTransportLayerInformation	,
	iE-Extensions	ProtocolExtensionContainer { { DLUPTNLInformation-ToBeSetup-ItemExtIEs } }	OPTIONAL,
	...
}

DLUPTNLInformation-ToBeSetup-ItemExtIEs 	F1AP-PROTOCOL-EXTENSION ::= {
	...
}

DRB-Activity-Item ::= SEQUENCE {
	dRBID			DRBID,
	dRB-Activity	DRB-Activity		OPTIONAL,
	iE-Extensions	ProtocolExtensionContainer { { DRB-Activity-ItemExtIEs } }	OPTIONAL,
	...
}

DRB-Activity-ItemExtIEs 	F1AP-PROTOCOL-EXTENSION ::= {
	...
}

DRB-Activity ::= ENUMERATED {active, not-active}

DRBID ::= INTEGER (1..32, ...)

DRBs-FailedToBeModified-Item	::= SEQUENCE {
	dRBID		DRBID		,
	cause		Cause		OPTIONAL,
	iE-Extensions	ProtocolExtensionContainer { { DRBs-FailedToBeModified-ItemExtIEs } }	OPTIONAL,
	...
}

DRBs-FailedToBeModified-ItemExtIEs 	F1AP-PROTOCOL-EXTENSION ::= {
	...
}

DRBs-FailedToBeSetup-Item	::= SEQUENCE {
	dRBID	DRBID,
	cause	Cause	OPTIONAL,
	iE-Extensions	ProtocolExtensionContainer { { DRBs-FailedToBeSetup-ItemExtIEs } }	OPTIONAL,
	...
}

DRBs-FailedToBeSetup-ItemExtIEs 	F1AP-PROTOCOL-EXTENSION ::= {
	...
}


DRBs-FailedToBeSetupMod-Item	::= SEQUENCE {
	dRBID		DRBID	,
	cause		Cause			OPTIONAL ,
	iE-Extensions	ProtocolExtensionContainer { { DRBs-FailedToBeSetupMod-ItemExtIEs } }	OPTIONAL,
	...
}

DRBs-FailedToBeSetupMod-ItemExtIEs 	F1AP-PROTOCOL-EXTENSION ::= {
	...
}

DRB-Information	::=	SEQUENCE {
	dRB-QoS		QoSFlowLevelQoSParameters,
	sNSSAI		SNSSAI,
	notificationControl		NotificationControl		OPTIONAL,
	flows-Mapped-To-DRB-List	Flows-Mapped-To-DRB-List,
	iE-Extensions	ProtocolExtensionContainer { { DRB-Information-ItemExtIEs } }	OPTIONAL
}

DRB-Information-ItemExtIEs 	F1AP-PROTOCOL-EXTENSION ::= {
	...
}

DRBs-Modified-Item	::= SEQUENCE {
	dRBID							DRBID,
	lCID								LCID		OPTIONAL,
	dLUPTNLInformation-ToBeSetup-List		DLUPTNLInformation-ToBeSetup-List,
	iE-Extensions	ProtocolExtensionContainer { { DRBs-Modified-ItemExtIEs } }	OPTIONAL,
	...
}

DRBs-Modified-ItemExtIEs 	F1AP-PROTOCOL-EXTENSION ::= {
	{ ID id-RLC-Status							CRITICALITY ignore	EXTENSION RLC-Status									PRESENCE optional }|
	{ ID id-AdditionalPDCPDuplicationTNL-List	CRITICALITY ignore	EXTENSION AdditionalPDCPDuplicationTNL-List		PRESENCE optional }|
	{ ID id-CurrentQoSParaSetIndex				CRITICALITY ignore	EXTENSION QoSParaSetIndex								PRESENCE optional },
	...
}

DRBs-ModifiedConf-Item	::= SEQUENCE {
	dRBID							DRBID,
	uLUPTNLInformation-ToBeSetup-List		ULUPTNLInformation-ToBeSetup-List	,
	iE-Extensions	ProtocolExtensionContainer { { DRBs-ModifiedConf-ItemExtIEs } }	OPTIONAL,
	...
}

DRBs-ModifiedConf-ItemExtIEs 	F1AP-PROTOCOL-EXTENSION ::= {
	{ ID id-AdditionalPDCPDuplicationTNL-List	CRITICALITY ignore	EXTENSION AdditionalPDCPDuplicationTNL-List			PRESENCE optional },
	...
}

DRB-Notify-Item ::= SEQUENCE {
	dRBID			DRBID,
	notification-Cause	Notification-Cause,
	iE-Extensions	ProtocolExtensionContainer { { DRB-Notify-ItemExtIEs } }	OPTIONAL,
	...
}

DRB-Notify-ItemExtIEs 	F1AP-PROTOCOL-EXTENSION ::= {
	{ ID id-CurrentQoSParaSetIndex	CRITICALITY ignore	EXTENSION QoSParaSetNotifyIndex	PRESENCE optional	},
	...
}

DRBs-Required-ToBeModified-Item	::= SEQUENCE {
	dRBID							DRBID,
	dLUPTNLInformation-ToBeSetup-List		DLUPTNLInformation-ToBeSetup-List	,
	iE-Extensions	ProtocolExtensionContainer { { DRBs-Required-ToBeModified-ItemExtIEs } }	OPTIONAL,
	...
}

DRBs-Required-ToBeModified-ItemExtIEs 	F1AP-PROTOCOL-EXTENSION ::= {
	{ ID id-RLC-Status			CRITICALITY ignore			EXTENSION RLC-Status				PRESENCE optional }|
	{ ID id-AdditionalPDCPDuplicationTNL-List	CRITICALITY ignore	EXTENSION AdditionalPDCPDuplicationTNL-List			PRESENCE optional },
	...
}

DRBs-Required-ToBeReleased-Item	::= SEQUENCE {
	dRBID		DRBID,
	iE-Extensions	ProtocolExtensionContainer { { DRBs-Required-ToBeReleased-ItemExtIEs } }	OPTIONAL,
	...
}

DRBs-Required-ToBeReleased-ItemExtIEs 	F1AP-PROTOCOL-EXTENSION ::= {
	...
}

DRBs-Setup-Item ::= SEQUENCE {
	dRBID							DRBID,
	lCID								LCID		OPTIONAL,
	dLUPTNLInformation-ToBeSetup-List		DLUPTNLInformation-ToBeSetup-List	,
	iE-Extensions	ProtocolExtensionContainer { { DRBs-Setup-ItemExtIEs } }	OPTIONAL,
	...
}

DRBs-Setup-ItemExtIEs 	F1AP-PROTOCOL-EXTENSION ::= {
	{ ID id-AdditionalPDCPDuplicationTNL-List	CRITICALITY ignore	EXTENSION AdditionalPDCPDuplicationTNL-List			PRESENCE optional }|
	{ ID id-CurrentQoSParaSetIndex				CRITICALITY ignore	EXTENSION QoSParaSetIndex									PRESENCE optional },
	...
}

DRBs-SetupMod-Item	::= SEQUENCE {
	dRBID							DRBID,
	lCID								LCID		OPTIONAL,
	dLUPTNLInformation-ToBeSetup-List		DLUPTNLInformation-ToBeSetup-List	,
	iE-Extensions	ProtocolExtensionContainer { { DRBs-SetupMod-ItemExtIEs } }	OPTIONAL,
	...
}

DRBs-SetupMod-ItemExtIEs 	F1AP-PROTOCOL-EXTENSION ::= {
	{ ID id-AdditionalPDCPDuplicationTNL-List	CRITICALITY ignore	EXTENSION AdditionalPDCPDuplicationTNL-List			PRESENCE optional }|
	{ ID id-CurrentQoSParaSetIndex				CRITICALITY ignore	EXTENSION QoSParaSetIndex									PRESENCE optional },
	...
}


DRBs-ToBeModified-Item	::= SEQUENCE {
	dRBID						DRBID,
	qoSInformation				QoSInformation	OPTIONAL,
	uLUPTNLInformation-ToBeSetup-List	ULUPTNLInformation-ToBeSetup-List	,
	uLConfiguration				ULConfiguration	OPTIONAL,
	iE-Extensions	ProtocolExtensionContainer { { DRBs-ToBeModified-ItemExtIEs } }	OPTIONAL,
	...
}

DRBs-ToBeModified-ItemExtIEs 	F1AP-PROTOCOL-EXTENSION ::= {
	{ ID id-DLPDCPSNLength						CRITICALITY ignore	EXTENSION PDCPSNLength										PRESENCE optional }|
	{ ID id-ULPDCPSNLength						CRITICALITY ignore	EXTENSION PDCPSNLength										PRESENCE optional }|
	{ID id-BearerTypeChange						CRITICALITY ignore	EXTENSION BearerTypeChange									PRESENCE optional}|
	{ ID id-RLCMode								CRITICALITY ignore	EXTENSION RLCMode											PRESENCE optional }|
	{ ID id-Duplication-Activation				CRITICALITY reject	EXTENSION DuplicationActivation							PRESENCE optional }|
	{ ID id-DC-Based-Duplication-Configured		CRITICALITY reject	EXTENSION DCBasedDuplicationConfigured					PRESENCE optional }|
	{ ID id-DC-Based-Duplication-Activation		CRITICALITY reject	EXTENSION DuplicationActivation							PRESENCE optional }|
	{ ID id-AdditionalPDCPDuplicationTNL-List	CRITICALITY ignore	EXTENSION AdditionalPDCPDuplicationTNL-List			PRESENCE optional }|
	{ ID id-RLCDuplicationInformation			CRITICALITY ignore	EXTENSION RLCDuplicationInformation						PRESENCE optional}|
	{ ID id-TransmissionStopIndicator			CRITICALITY ignore	EXTENSION TransmissionStopIndicator						PRESENCE optional}|
	{ ID id-CG-SDTindicatorMod					CRITICALITY reject	EXTENSION CG-SDTindicatorMod								PRESENCE optional },
	...
}

DRBs-ToBeReleased-Item	::= SEQUENCE {
	dRBID	DRBID,
	iE-Extensions	ProtocolExtensionContainer { { DRBs-ToBeReleased-ItemExtIEs } }	OPTIONAL,
	...
}

DRBs-ToBeReleased-ItemExtIEs 	F1AP-PROTOCOL-EXTENSION ::= {
	...
}

DRBs-ToBeSetup-Item ::= SEQUENCE	{
	dRBID						DRBID,
	qoSInformation				QoSInformation,
	uLUPTNLInformation-ToBeSetup-List	ULUPTNLInformation-ToBeSetup-List	,
	rLCMode						RLCMode,
	uLConfiguration				ULConfiguration	OPTIONAL,
	duplicationActivation		DuplicationActivation	OPTIONAL,
	iE-Extensions	ProtocolExtensionContainer { { DRBs-ToBeSetup-ItemExtIEs } }	OPTIONAL,
	...
}

DRBs-ToBeSetup-ItemExtIEs 	F1AP-PROTOCOL-EXTENSION ::= {
	{ ID id-DC-Based-Duplication-Configured		CRITICALITY reject	EXTENSION DCBasedDuplicationConfigured				PRESENCE optional }|
	{ ID id-DC-Based-Duplication-Activation		CRITICALITY reject	EXTENSION DuplicationActivation						PRESENCE optional }|
	{ ID id-DLPDCPSNLength						CRITICALITY ignore	EXTENSION PDCPSNLength									PRESENCE mandatory }|
	{ ID id-ULPDCPSNLength						CRITICALITY ignore	EXTENSION PDCPSNLength									PRESENCE optional }|
	{ ID id-AdditionalPDCPDuplicationTNL-List	CRITICALITY ignore	EXTENSION AdditionalPDCPDuplicationTNL-List		PRESENCE optional }|
	{ ID id-RLCDuplicationInformation			CRITICALITY ignore	EXTENSION RLCDuplicationInformation					PRESENCE optional}|
	{ ID id-SDTRLCBearerConfiguration			CRITICALITY ignore	EXTENSION SDTRLCBearerConfiguration					PRESENCE optional },
	...
}


DRBs-ToBeSetupMod-Item	::= SEQUENCE {
	dRBID						DRBID,
	qoSInformation				QoSInformation,
	uLUPTNLInformation-ToBeSetup-List		ULUPTNLInformation-ToBeSetup-List,
	rLCMode						RLCMode,
	uLConfiguration				ULConfiguration	OPTIONAL,
	duplicationActivation		DuplicationActivation	OPTIONAL,
	iE-Extensions	ProtocolExtensionContainer { { DRBs-ToBeSetupMod-ItemExtIEs } }	OPTIONAL,
	...
}

DRBs-ToBeSetupMod-ItemExtIEs 	F1AP-PROTOCOL-EXTENSION ::= {
	{ ID id-DC-Based-Duplication-Configured		CRITICALITY reject	EXTENSION DCBasedDuplicationConfigured				PRESENCE optional }|
	{ ID id-DC-Based-Duplication-Activation		CRITICALITY reject	EXTENSION DuplicationActivation						PRESENCE optional }|
	{ ID id-DLPDCPSNLength						CRITICALITY ignore	EXTENSION PDCPSNLength									PRESENCE optional }|
	{ ID id-ULPDCPSNLength						CRITICALITY ignore	EXTENSION PDCPSNLength									PRESENCE optional }|
	{ ID id-AdditionalPDCPDuplicationTNL-List	CRITICALITY ignore	EXTENSION AdditionalPDCPDuplicationTNL-List		PRESENCE optional }|
	{ ID id-RLCDuplicationInformation			CRITICALITY ignore	EXTENSION RLCDuplicationInformation					PRESENCE optional}|
	{ ID id-CG-SDTindicatorSetup				CRITICALITY reject	EXTENSION CG-SDTindicatorSetup						PRESENCE optional },
	...
}

DRXCycle	::= SEQUENCE {
	longDRXCycleLength	LongDRXCycleLength,
	shortDRXCycleLength		ShortDRXCycleLength	OPTIONAL,
	shortDRXCycleTimer	ShortDRXCycleTimer OPTIONAL,
	iE-Extensions		ProtocolExtensionContainer { { DRXCycle-ExtIEs} } OPTIONAL,
	...
}

DRXCycle-ExtIEs F1AP-PROTOCOL-EXTENSION ::= {
	...
}

DRX-Config ::= OCTET STRING

DRXConfigurationIndicator	::=	ENUMERATED{	release, ...}

DRX-LongCycleStartOffset ::= INTEGER (0..10239)

DSInformationList ::= SEQUENCE (SIZE(0..maxnoofDSInfo)) OF DSCP

DSCP ::= BIT STRING (SIZE (6))

DUtoCURRCContainer ::= OCTET STRING

DUCURadioInformationType ::= CHOICE {
	rIM								DUCURIMInformation,
	choice-extension				ProtocolIE-SingleContainer { { DUCURadioInformationType-ExtIEs} }
}

DUCURadioInformationType-ExtIEs F1AP-PROTOCOL-IES ::= {
	...
}

DUCURIMInformation ::= SEQUENCE {
	victimgNBSetID				GNBSetID,
	rIMRSDetectionStatus		RIMRSDetectionStatus,
	aggressorCellList			AggressorCellList,
	iE-Extensions				ProtocolExtensionContainer { { DUCURIMInformation-ExtIEs} }		OPTIONAL
}

DUCURIMInformation-ExtIEs F1AP-PROTOCOL-EXTENSION ::= {
	...
}

DUF-Slot-Config-Item 	::=	CHOICE {
	explicitFormat				ExplicitFormat,
	implicitFormat				ImplicitFormat,
	choice-extension				ProtocolIE-SingleContainer { { DUF-Slot-Config-Item-ExtIEs} }
}

DUF-Slot-Config-Item-ExtIEs F1AP-PROTOCOL-IES ::= {
	...
}
DUF-Slot-Config-List	::= SEQUENCE (SIZE(1..maxnoofDUFSlots)) OF DUF-Slot-Config-Item

DUFSlotformatIndex ::= INTEGER(0..254)

DUFTransmissionPeriodicity ::= ENUMERATED { ms0p5, ms0p625, ms1, ms1p25, ms2, ms2p5, ms5, ms10, ...}

DU-RX-MT-RX ::= ENUMERATED {supported, not-supported }

DU-TX-MT-TX ::= ENUMERATED {supported, not-supported }

DU-RX-MT-TX ::= ENUMERATED {supported, not-supported }

DU-TX-MT-RX ::= ENUMERATED {supported, not-supported }

DU-RX-MT-RX-Extend ::= ENUMERATED {supported, not-supported, supported-and-FDM-required, ...}

DU-TX-MT-TX-Extend ::= ENUMERATED {supported, not-supported, supported-and-FDM-required, ...}

DU-RX-MT-TX-Extend ::= ENUMERATED {supported, not-supported, supported-and-FDM-required, ...}

DU-TX-MT-RX-Extend ::= ENUMERATED {supported, not-supported, supported-and-FDM-required, ...}

DUtoCURRCInformation ::= SEQUENCE {
	cellGroupConfig		CellGroupConfig,
	measGapConfig			MeasGapConfig	OPTIONAL,
	requestedP-MaxFR1				OCTET STRING				OPTIONAL,
	iE-Extensions				ProtocolExtensionContainer { { DUtoCURRCInformation-ExtIEs} } OPTIONAL,
	...
}

DUtoCURRCInformation-ExtIEs F1AP-PROTOCOL-EXTENSION ::= {
	{ ID id-DRX-LongCycleStartOffset			CRITICALITY ignore	EXTENSION DRX-LongCycleStartOffset				PRESENCE optional }|
	{ ID id-SelectedBandCombinationIndex		CRITICALITY ignore	EXTENSION SelectedBandCombinationIndex			PRESENCE optional }|
	{ ID id-SelectedFeatureSetEntryIndex		CRITICALITY ignore	EXTENSION SelectedFeatureSetEntryIndex			PRESENCE optional }|
	{ ID id-Ph-InfoSCG							CRITICALITY ignore	EXTENSION Ph-InfoSCG								PRESENCE optional }|
	{ ID id-RequestedBandCombinationIndex		CRITICALITY ignore	EXTENSION RequestedBandCombinationIndex		PRESENCE optional }|
	{ ID id-RequestedFeatureSetEntryIndex		CRITICALITY ignore	EXTENSION RequestedFeatureSetEntryIndex		PRESENCE optional }|
	{ ID id-DRX-Config							CRITICALITY ignore	EXTENSION DRX-Config								PRESENCE optional }|
	{ ID id-PDCCH-BlindDetectionSCG				CRITICALITY ignore	EXTENSION PDCCH-BlindDetectionSCG				PRESENCE optional }|
	{ ID id-Requested-PDCCH-BlindDetectionSCG	CRITICALITY ignore	EXTENSION Requested-PDCCH-BlindDetectionSCG	PRESENCE optional }|
	{ ID id-Ph-InfoMCG							CRITICALITY ignore	EXTENSION Ph-InfoMCG								PRESENCE optional }|
	{ ID id-MeasGapSharingConfig				CRITICALITY ignore	EXTENSION MeasGapSharingConfig					PRESENCE optional }|
	{ ID id-SL-PHY-MAC-RLC-Config				CRITICALITY ignore	EXTENSION SL-PHY-MAC-RLC-Config					PRESENCE optional }|
	{ ID id-SL-ConfigDedicatedEUTRA-Info		CRITICALITY ignore	EXTENSION SL-ConfigDedicatedEUTRA-Info			PRESENCE optional }|
	{ ID id-RequestedP-MaxFR2					CRITICALITY ignore	EXTENSION RequestedP-MaxFR2							PRESENCE optional }|
	{ ID id-SDT-MAC-PHY-CG-Config				CRITICALITY ignore	EXTENSION SDT-MAC-PHY-CG-Config							PRESENCE optional }|
	{ ID id-MUSIM-GapConfig						CRITICALITY ignore	EXTENSION MUSIM-GapConfig							PRESENCE optional }|
	{ ID id-SL-RLC-ChannelToAddModList			CRITICALITY ignore	EXTENSION SL-RLC-ChannelToAddModList			PRESENCE optional }|
	{ ID id-InterFrequencyConfig-NoGap			CRITICALITY ignore	EXTENSION InterFrequencyConfig-NoGap			PRESENCE optional }|
	{ ID id-UL-GapFR2-Config					CRITICALITY ignore	EXTENSION UL-GapFR2-Config							PRESENCE optional }|
	{ ID id-TwoPHRModeMCG						CRITICALITY ignore	EXTENSION TwoPHRModeMCG								PRESENCE optional }|
	{ ID id-TwoPHRModeSCG						CRITICALITY ignore	EXTENSION TwoPHRModeSCG								PRESENCE optional },
	...
}

DuplicationActivation ::= ENUMERATED{active,inactive,... }

DuplicationIndication ::= ENUMERATED {true, ... , false }

DuplicationState ::= ENUMERATED {
	active,
	inactive,
	...
}

Dynamic5QIDescriptor	::= SEQUENCE {
	qoSPriorityLevel					INTEGER (1..127),
	packetDelayBudget					PacketDelayBudget,
	packetErrorRate						PacketErrorRate,
	fiveQI								INTEGER (0..255, ...)								OPTIONAL,
	delayCritical						ENUMERATED {delay-critical, non-delay-critical}		OPTIONAL,
	-- C-ifGBRflow: This IE shall be present if the GBR QoS Flow Information IE is present in the QoS Flow Level QoS Parameters IE.
	averagingWindow 					AveragingWindow										OPTIONAL,
	-- C-ifGBRflow: This IE shall be present if the GBR QoS Flow Information IE is present in the QoS Flow Level QoS Parameters IE.
	maxDataBurstVolume					MaxDataBurstVolume									OPTIONAL,
	iE-Extensions					ProtocolExtensionContainer { { Dynamic5QIDescriptor-ExtIEs } } OPTIONAL
}

Dynamic5QIDescriptor-ExtIEs F1AP-PROTOCOL-EXTENSION ::= {
	{ ID id-ExtendedPacketDelayBudget			CRITICALITY ignore	EXTENSION ExtendedPacketDelayBudget		PRESENCE optional		}|
	{ ID id-CNPacketDelayBudgetDownlink			CRITICALITY ignore	EXTENSION ExtendedPacketDelayBudget		PRESENCE optional		}|
	{ ID id-CNPacketDelayBudgetUplink			CRITICALITY ignore	EXTENSION ExtendedPacketDelayBudget		PRESENCE optional		},
	...
}

DynamicPQIDescriptor	::= SEQUENCE {
	resourceType						ENUMERATED {gbr, non-gbr, delay-critical-grb, ...}	OPTIONAL,
	qoSPriorityLevel					INTEGER (1..8, ...),
	packetDelayBudget					PacketDelayBudget,
	packetErrorRate						PacketErrorRate,
	averagingWindow 					AveragingWindow										OPTIONAL,
	-- C-ifGBRflow: This IE shall be present if the GBR QoS Flow Information IE is present in the QoS Flow Level QoS Parameters IE.
	maxDataBurstVolume					MaxDataBurstVolume									OPTIONAL,
	iE-Extensions						ProtocolExtensionContainer { { DynamicPQIDescriptor-ExtIEs } } OPTIONAL
}

DynamicPQIDescriptor-ExtIEs F1AP-PROTOCOL-EXTENSION ::= {
	...
}

-- E


E-CID-MeasurementQuantities ::= SEQUENCE (SIZE (1.. maxnoofMeasE-CID)) OF ProtocolIE-SingleContainer { {E-CID-MeasurementQuantities-ItemIEs} }

E-CID-MeasurementQuantities-ItemIEs F1AP-PROTOCOL-IES ::= {
	{ ID id-E-CID-MeasurementQuantities-Item	CRITICALITY reject	TYPE E-CID-MeasurementQuantities-Item		PRESENCE mandatory}
}

E-CID-MeasurementQuantities-Item ::= SEQUENCE {
	e-CIDmeasurementQuantitiesValue				E-CID-MeasurementQuantitiesValue,
	iE-Extensions								ProtocolExtensionContainer { { E-CID-MeasurementQuantitiesValue-ExtIEs} } OPTIONAL
}

E-CID-MeasurementQuantitiesValue-ExtIEs F1AP-PROTOCOL-EXTENSION ::= {
	...
}

E-CID-MeasurementQuantitiesValue ::= ENUMERATED {
	default,
	angleOfArrivalNR,
	... ,
	timingAdvanceNR
}

E-CID-MeasurementResult ::= SEQUENCE {
	geographicalCoordinates		GeographicalCoordinates 	OPTIONAL,
	measuredResults-List		E-CID-MeasuredResults-List 	OPTIONAL,
	iE-Extensions					ProtocolExtensionContainer { { E-CID-MeasurementResult-ExtIEs} } OPTIONAL
}

E-CID-MeasurementResult-ExtIEs F1AP-PROTOCOL-EXTENSION ::= {
	...
}

E-CID-MeasuredResults-List ::= SEQUENCE (SIZE(1..maxnoofMeasE-CID)) OF E-CID-MeasuredResults-Item

E-CID-MeasuredResults-Item ::= SEQUENCE {
	e-CID-MeasuredResults-Value 	E-CID-MeasuredResults-Value,
	iE-Extensions			ProtocolExtensionContainer {{ E-CID-MeasuredResults-Item-ExtIEs }}	 OPTIONAL
}

E-CID-MeasuredResults-Item-ExtIEs F1AP-PROTOCOL-EXTENSION ::= {
	...
}

E-CID-MeasuredResults-Value ::= CHOICE {
	valueAngleofArrivalNR	UL-AoA,
	choice-extension		ProtocolIE-SingleContainer { { E-CID-MeasuredResults-Value-ExtIEs} }
}

E-CID-MeasuredResults-Value-ExtIEs F1AP-PROTOCOL-IES ::= {
	{ ID id-NR-TADV			CRITICALITY ignore	TYPE NR-TADV	PRESENCE mandatory	},
	...
}

E-CID-ReportCharacteristics ::= ENUMERATED {
	onDemand,
	periodic,
	...
}

EgressBHRLCCHList ::= SEQUENCE (SIZE(1..maxnoofEgressLinks)) OF EgressBHRLCCHItem

EgressBHRLCCHItem ::= SEQUENCE {
	nextHopBAPAddress 		BAPAddress,
	bHRLCChannelID			BHRLCChannelID,
	iE-Extensions			ProtocolExtensionContainer {{EgressBHRLCCHItemExtIEs }}	 OPTIONAL
}

EgressBHRLCCHItemExtIEs F1AP-PROTOCOL-EXTENSION ::= {
	...
}

EgressNonF1terminatingTopologyIndicator ::= ENUMERATED {true, ...}

Endpoint-IP-address-and-port ::=SEQUENCE {
	endpointIPAddress TransportLayerAddress,
	iE-Extensions					ProtocolExtensionContainer { { Endpoint-IP-address-and-port-ExtIEs} } OPTIONAL
}

Endpoint-IP-address-and-port-ExtIEs F1AP-PROTOCOL-EXTENSION ::= {
	{ ID id-portNumber	CRITICALITY reject	EXTENSION PortNumber		PRESENCE optional},
	...
}

EnergyDetectionThreshold ::= INTEGER (-100..-50, ...)

ExtendedAvailablePLMN-List ::= SEQUENCE (SIZE(1..maxnoofExtendedBPLMNs)) OF ExtendedAvailablePLMN-Item

ExtendedAvailablePLMN-Item ::= SEQUENCE {
	pLMNIdentity			PLMN-Identity,
	iE-Extensions		ProtocolExtensionContainer { { ExtendedAvailablePLMN-Item-ExtIEs} } OPTIONAL
}

ExplicitFormat ::=	SEQUENCE {
	permutation			Permutation,
	noofDownlinkSymbols	NoofDownlinkSymbols		OPTIONAL,
	noofUplinkSymbols	NoofUplinkSymbols		OPTIONAL,
	iE-Extensions		ProtocolExtensionContainer { { ExplicitFormat-ExtIEs} } OPTIONAL
}

ExplicitFormat-ExtIEs F1AP-PROTOCOL-EXTENSION ::= {
	...
}

ExtendedAvailablePLMN-Item-ExtIEs F1AP-PROTOCOL-EXTENSION ::= {
	...
}

ExtendedServedPLMNs-List ::= SEQUENCE (SIZE(1.. maxnoofExtendedBPLMNs)) OF ExtendedServedPLMNs-Item

ExtendedServedPLMNs-Item ::= SEQUENCE {
	pLMN-Identity				PLMN-Identity,
	tAISliceSupportList 		SliceSupportList	OPTIONAL,
	iE-Extensions				ProtocolExtensionContainer { { ExtendedServedPLMNs-ItemExtIEs} } OPTIONAL,
	...
}

ExtendedServedPLMNs-ItemExtIEs F1AP-PROTOCOL-EXTENSION ::= {
	{ ID id-NPNSupportInfo				CRITICALITY reject	EXTENSION NPNSupportInfo				PRESENCE optional	}|
	{ ID id-ExtendedTAISliceSupportList	CRITICALITY reject	EXTENSION ExtendedSliceSupportList		PRESENCE optional	}|
	{ ID id-TAINSAGSupportList			CRITICALITY ignore	EXTENSION NSAGSupportList				PRESENCE optional},
	...
}

ExtendedSliceSupportList ::= SEQUENCE (SIZE(1.. maxnoofExtSliceItems)) OF SliceSupportItem

ExtendedUEIdentityIndexValue ::= BIT STRING (SIZE(16))

EUTRACells-List  ::= SEQUENCE (SIZE (1.. maxCellineNB)) OF EUTRACells-List-item

EUTRACells-List-item ::= SEQUENCE {
	eUTRA-Cell-ID					EUTRA-Cell-ID,
	served-EUTRA-Cells-Information	Served-EUTRA-Cells-Information,
	iE-Extensions ProtocolExtensionContainer { { EUTRACells-List-itemExtIEs } }    OPTIONAL
}

EUTRACells-List-itemExtIEs    F1AP-PROTOCOL-EXTENSION ::= {
	...
}


EUTRA-Cell-ID ::= BIT STRING (SIZE(28))

EUTRA-Coex-FDD-Info ::= SEQUENCE {
	uL-EARFCN						ExtendedEARFCN					OPTIONAL,
	dL-EARFCN						ExtendedEARFCN,
	uL-Transmission-Bandwidth		EUTRA-Transmission-Bandwidth	OPTIONAL,
	dL-Transmission-Bandwidth		EUTRA-Transmission-Bandwidth,
	iE-Extensions					ProtocolExtensionContainer { {EUTRA-Coex-FDD-Info-ExtIEs} } OPTIONAL,
	...
}

EUTRA-Coex-FDD-Info-ExtIEs F1AP-PROTOCOL-EXTENSION ::= {
	...
}

EUTRA-Coex-Mode-Info ::= CHOICE {
	fDD		EUTRA-Coex-FDD-Info,
	tDD		EUTRA-Coex-TDD-Info,
	...
}

EUTRA-Coex-TDD-Info ::= SEQUENCE {
	eARFCN							ExtendedEARFCN,
	transmission-Bandwidth			EUTRA-Transmission-Bandwidth,
	subframeAssignment				EUTRA-SubframeAssignment,
	specialSubframe-Info			EUTRA-SpecialSubframe-Info,
	iE-Extensions					ProtocolExtensionContainer { {EUTRA-Coex-TDD-Info-ExtIEs} } OPTIONAL,
	...
}
EUTRA-Coex-TDD-Info-ExtIEs F1AP-PROTOCOL-EXTENSION ::= {
	...
}
EUTRA-CyclicPrefixDL ::= ENUMERATED {
	normal,
	extended,
	...
}

EUTRA-CyclicPrefixUL ::= ENUMERATED {
	normal,
	extended,
	...
}

EUTRA-PRACH-Configuration ::= SEQUENCE {
	rootSequenceIndex						INTEGER (0..837),
	zeroCorrelationIndex					INTEGER (0..15),
	highSpeedFlag							BOOLEAN,
	prach-FreqOffset						INTEGER (0..94),
	prach-ConfigIndex						INTEGER (0..63)		OPTIONAL,
	-- C-ifTDD: This IE shall be present if the EUTRA-Mode-Info IE in the Resource Coordination E-UTRA Cell Information IE is set to the value "TDD"
	iE-Extensions							ProtocolExtensionContainer { {EUTRA-PRACH-Configuration-ExtIEs} }	OPTIONAL,
	...
}

EUTRA-PRACH-Configuration-ExtIEs F1AP-PROTOCOL-EXTENSION ::= {
	...
}


EUTRA-SpecialSubframe-Info ::= SEQUENCE {
	specialSubframePatterns		EUTRA-SpecialSubframePatterns,
	cyclicPrefixDL				EUTRA-CyclicPrefixDL,
	cyclicPrefixUL				EUTRA-CyclicPrefixUL,
	iE-Extensions				ProtocolExtensionContainer { { EUTRA-SpecialSubframe-Info-ExtIEs} } OPTIONAL,
	...
}

EUTRA-SpecialSubframe-Info-ExtIEs F1AP-PROTOCOL-EXTENSION ::= {
	...
}

EUTRA-SpecialSubframePatterns ::= ENUMERATED {
	ssp0,
	ssp1,
	ssp2,
	ssp3,
	ssp4,
	ssp5,
	ssp6,
	ssp7,
	ssp8,
	ssp9,
	ssp10,
	...
}

EUTRA-SubframeAssignment ::= ENUMERATED {
	sa0,
	sa1,
	sa2,
	sa3,
	sa4,
	sa5,
	sa6,
	...
}

EUTRA-Transmission-Bandwidth ::= ENUMERATED {
	bw6,
	bw15,
	bw25,
	bw50,
	bw75,
	bw100,
	...
}

EUTRANQoS	::= SEQUENCE {
	qCI								QCI,
	allocationAndRetentionPriority	AllocationAndRetentionPriority,
	gbrQosInformation				GBR-QosInformation									OPTIONAL,
	iE-Extensions					ProtocolExtensionContainer { { EUTRANQoS-ExtIEs} }	OPTIONAL,
	...
}

EUTRANQoS-ExtIEs F1AP-PROTOCOL-EXTENSION ::= {
{ ID id-ENBDLTNLAddress		CRITICALITY ignore	EXTENSION TransportLayerAddress	PRESENCE optional	},
	...
}

ExecuteDuplication ::= ENUMERATED{true,...}

ExtendedEARFCN ::= INTEGER (0..262143)

EUTRA-Mode-Info ::= CHOICE {
	eUTRAFDD		EUTRA-FDD-Info,
	eUTRATDD		EUTRA-TDD-Info,
	choice-extension	ProtocolIE-SingleContainer { { EUTRA-Mode-Info-ExtIEs} }
}

EUTRA-Mode-Info-ExtIEs F1AP-PROTOCOL-IES ::= {
	...
}

EUTRA-NR-CellResourceCoordinationReq-Container	::= OCTET STRING

EUTRA-NR-CellResourceCoordinationReqAck-Container	::= OCTET STRING

EUTRA-FDD-Info ::= SEQUENCE {
	uL-offsetToPointA				OffsetToPointA,
	dL-offsetToPointA				OffsetToPointA,
	iE-Extensions					ProtocolExtensionContainer { {EUTRA-FDD-Info-ExtIEs} } OPTIONAL,
	...
}

EUTRA-FDD-Info-ExtIEs F1AP-PROTOCOL-EXTENSION ::= {
	...
}

EUTRA-TDD-Info ::= SEQUENCE {
	offsetToPointA					OffsetToPointA,
	iE-Extensions					ProtocolExtensionContainer { {EUTRA-TDD-Info-ExtIEs} } OPTIONAL,
	...
}

EUTRA-TDD-Info-ExtIEs F1AP-PROTOCOL-EXTENSION ::= {
	...
}

EventType ::= ENUMERATED {
	on-demand,
	periodic,
	stop,
	...
}

ExtendedPacketDelayBudget ::= INTEGER (1..65535, ...)

Expected-UL-AoA ::= SEQUENCE {
	expected-Azimuth-AoA	Expected-Azimuth-AoA,
	expected-Zenith-AoA		Expected-Zenith-AoA		OPTIONAL,
	iE-extensions			ProtocolExtensionContainer { { Expected-UL-AoA-ExtIEs } }	OPTIONAL,
	...
}
Expected-UL-AoA-ExtIEs F1AP-PROTOCOL-EXTENSION ::= {
	...
}

Expected-ZoA-only ::= SEQUENCE {
	expected-ZoA-only	Expected-Zenith-AoA,
	iE-extensions		ProtocolExtensionContainer { { Expected-ZoA-only-ExtIEs } }	OPTIONAL,
	...
}

Expected-ZoA-only-ExtIEs F1AP-PROTOCOL-EXTENSION ::= {
	...
}

Expected-Azimuth-AoA ::= SEQUENCE {
	expected-Azimuth-AoA-value			Expected-Value-AoA,
	expected-Azimuth-AoA-uncertainty	Uncertainty-range-AoA,
	iE-Extensions						ProtocolExtensionContainer { { Expected-Azimuth-AoA-ExtIEs } }		OPTIONAL,
	...
}

Expected-Azimuth-AoA-ExtIEs	F1AP-PROTOCOL-EXTENSION ::= {
	...
}
Expected-Zenith-AoA ::= SEQUENCE {
	expected-Zenith-AoA-value			Expected-Value-ZoA,
	expected-Zenith-AoA-uncertainty		Uncertainty-range-ZoA,
	iE-Extensions						ProtocolExtensionContainer { { Expected-Zenith-AoA-ExtIEs } }		OPTIONAL,
	...
}

Expected-Zenith-AoA-ExtIEs	F1AP-PROTOCOL-EXTENSION ::= {
	...
}

Expected-Value-AoA ::= INTEGER (0..3599)

Expected-Value-ZoA ::= INTEGER (0..1799)

-- F

F1CPathNSA ::= ENUMERATED {lte, nr, both}

F1CTransferPath ::= SEQUENCE {
	f1CPathNSA						F1CPathNSA,
	iE-Extensions					ProtocolExtensionContainer { { F1CTransferPath-ExtIEs} } OPTIONAL,
	...
}

F1CTransferPath-ExtIEs F1AP-PROTOCOL-EXTENSION ::= {
	...
}

F1CPathNRDC ::= ENUMERATED {mcg, scg, both}

F1CTransferPathNRDC ::= SEQUENCE {
	f1CPathNRDC						F1CPathNRDC,
	iE-Extensions					ProtocolExtensionContainer { { F1CTransferPathNRDC-ExtIEs} } OPTIONAL,
	...
}

F1CTransferPathNRDC-ExtIEs F1AP-PROTOCOL-EXTENSION ::= {
	...
}


FDD-Info ::= SEQUENCE {
	uL-NRFreqInfo						NRFreqInfo,
	dL-NRFreqInfo						NRFreqInfo,
	uL-Transmission-Bandwidth			Transmission-Bandwidth,
	dL-Transmission-Bandwidth			Transmission-Bandwidth,
	iE-Extensions						ProtocolExtensionContainer { {FDD-Info-ExtIEs} } OPTIONAL,
	...
}

FDD-Info-ExtIEs F1AP-PROTOCOL-EXTENSION ::= {
	{ ID id-ULCarrierList				CRITICALITY ignore	EXTENSION NRCarrierList				PRESENCE optional }|
	{ ID id-DLCarrierList				CRITICALITY ignore EXTENSION NRCarrierList				PRESENCE optional },
	...
}

FDD-InfoRel16 ::= SEQUENCE {
	uL-FreqInfo										FreqInfoRel16													OPTIONAL,
	sUL-FreqInfo									FreqInfoRel16													OPTIONAL,
	iE-Extensions									ProtocolExtensionContainer { {FDD-InfoRel16-ExtIEs} }		OPTIONAL,
	...
}

FDD-InfoRel16-ExtIEs F1AP-PROTOCOL-EXTENSION ::= {
	...
}

FiveG-ProSeAuthorized ::= SEQUENCE {
	fiveG-proSeDirectDiscovery					FiveG-ProSeDirectDiscovery									OPTIONAL,
	fiveG-proSeDirectCommunication				FiveG-ProSeDirectCommunication								OPTIONAL,
	fiveG-ProSeLayer2UEtoNetworkRelay			FiveG-ProSeLayer2UEtoNetworkRelay							OPTIONAL,
	fiveG-ProSeLayer3UEtoNetworkRelay			FiveG-ProSeLayer3UEtoNetworkRelay							OPTIONAL,
	fiveG-ProSeLayer2RemoteUE					FiveG-ProSeLayer2RemoteUE									OPTIONAL,
	iE-Extensions								ProtocolExtensionContainer { {FiveG-ProSeAuthorized-ExtIEs} }	OPTIONAL,
	...
}

FiveG-ProSeAuthorized-ExtIEs F1AP-PROTOCOL-EXTENSION ::= {
	...
}

FiveG-ProSeDirectDiscovery ::= ENUMERATED {
	authorized,
	not-authorized,
	...
}

FiveG-ProSeDirectCommunication ::= ENUMERATED {
	authorized,
	not-authorized,
	...
}

FiveG-ProSeLayer2UEtoNetworkRelay ::= ENUMERATED {
	authorized,
	not-authorized,
	...
}

FiveG-ProSeLayer3UEtoNetworkRelay ::= ENUMERATED {
	authorized,
	not-authorized,
	...
}

FiveG-ProSeLayer2RemoteUE ::= ENUMERATED {
	authorized,
	not-authorized,
	...
}

Flows-Mapped-To-DRB-List	::=	SEQUENCE (SIZE(1.. maxnoofQoSFlows)) OF Flows-Mapped-To-DRB-Item

Flows-Mapped-To-DRB-Item 	::= SEQUENCE {
	qoSFlowIdentifier							QoSFlowIdentifier,
	qoSFlowLevelQoSParameters				QoSFlowLevelQoSParameters,
	iE-Extensions							ProtocolExtensionContainer { { Flows-Mapped-To-DRB-ItemExtIEs} } OPTIONAL
}

Flows-Mapped-To-DRB-ItemExtIEs 	F1AP-PROTOCOL-EXTENSION ::= {
	{ID id-QoSFlowMappingIndication		CRITICALITY ignore	EXTENSION QoSFlowMappingIndication			PRESENCE optional}|
	{ID id-TSCTrafficCharacteristics	CRITICALITY ignore	EXTENSION TSCTrafficCharacteristics			PRESENCE optional},
	...
}

FR1-Bandwidth ::= ENUMERATED {bw5, bw10, bw20, bw40, bw50, bw80, bw100, ...}

FR2-Bandwidth ::= ENUMERATED {bw50, bw100, bw200, bw400, ..., bw800, bw1600, bw2000}

FreqBandNrItem ::= SEQUENCE {
	freqBandIndicatorNr 		INTEGER (1..1024,...),
	supportedSULBandList		SEQUENCE (SIZE(0..maxnoofNrCellBands)) OF SupportedSULFreqBandItem,
	iE-Extensions				ProtocolExtensionContainer { {FreqBandNrItem-ExtIEs} } OPTIONAL,
	...
}

FreqBandNrItem-ExtIEs 	F1AP-PROTOCOL-EXTENSION ::= {
	...
}

FreqDomainLength ::= CHOICE {
	l839							L839Info,
	l139							L139Info,
	choice-extension				ProtocolIE-SingleContainer { {FreqDomainLength-ExtIEs} }
}

FreqDomainLength-ExtIEs F1AP-PROTOCOL-IES ::= {
	{ ID id-L571Info	CRITICALITY reject	TYPE L571Info PRESENCE mandatory}|
	{ ID id-L1151Info	CRITICALITY reject	TYPE L1151Info PRESENCE mandatory},
	...
}

FreqInfoRel16 ::=  SEQUENCE {
	nRARFCN											INTEGER (0..maxNRARFCN)											OPTIONAL,
	frequencyShift7p5khz							FrequencyShift7p5khz											OPTIONAL,
	carrierList										NRCarrierList													OPTIONAL,
	iE-Extensions									ProtocolExtensionContainer { { FreqInfoRel16-ExtIEs} }		OPTIONAL,
	...
}

FreqInfoRel16-ExtIEs		F1AP-PROTOCOL-EXTENSION ::= {
	...
}

FrequencyShift7p5khz ::= ENUMERATED {false, true, ...}

Frequency-Domain-HSNA-Configuration-List ::= SEQUENCE (SIZE(1..maxnoofRBsetsPerCell)) OF Frequency-Domain-HSNA-Configuration-Item

Frequency-Domain-HSNA-Configuration-Item::= SEQUENCE {
	rBSetIndex 		    INTEGER (0..maxnoofRBsetsPerCell-1, ...),
	frequency-Domain-HSNA-Slot-Configuration-List				Frequency-Domain-HSNA-Slot-Configuration-List,
	iE-Extensions		ProtocolExtensionContainer { { Frequency-Domain-HSNA-Configuration-Item-ExtIEs} } OPTIONAL
}


Frequency-Domain-HSNA-Configuration-Item-ExtIEs F1AP-PROTOCOL-EXTENSION ::= {
	...
}

Frequency-Domain-HSNA-Slot-Configuration-List ::= SEQUENCE (SIZE(1..maxnoofHSNASlots)) OF Frequency-Domain-HSNA-Slot-Configuration-Item

Frequency-Domain-HSNA-Slot-Configuration-Item::= SEQUENCE {
	slotIndex				INTEGER (0..5119)		OPTIONAL,
	hSNADownlink			HSNADownlink 			OPTIONAL,
	hSNAUplink				HSNAUplink 				OPTIONAL,
	hSNAFlexible			HSNAFlexible 			OPTIONAL,
	iE-Extensions			ProtocolExtensionContainer { { Frequency-Domain-HSNA-Slot-Configuration-Item-ExtIEs } } OPTIONAL
}

Frequency-Domain-HSNA-Slot-Configuration-Item-ExtIEs F1AP-PROTOCOL-EXTENSION ::= {
	...
}

FullConfiguration ::= ENUMERATED {full, ...}

FlowsMappedToSLDRB-List ::= SEQUENCE (SIZE(1.. maxnoofPC5QoSFlows)) OF FlowsMappedToSLDRB-Item

FlowsMappedToSLDRB-Item ::= SEQUENCE {
	pc5QoSFlowIdentifier			PC5QoSFlowIdentifier,
	iE-Extensions					ProtocolExtensionContainer { {FlowsMappedToSLDRB-Item-ExtIEs} } OPTIONAL,
	...
}

FlowsMappedToSLDRB-Item-ExtIEs	F1AP-PROTOCOL-EXTENSION ::= {
	...
}

-- G


GBR-QosInformation ::= SEQUENCE {
	e-RAB-MaximumBitrateDL			BitRate,
	e-RAB-MaximumBitrateUL			BitRate,
	e-RAB-GuaranteedBitrateDL		BitRate,
	e-RAB-GuaranteedBitrateUL		BitRate,
	iE-Extensions					ProtocolExtensionContainer { { GBR-QosInformation-ExtIEs} } OPTIONAL,
	...
}

GBR-QosInformation-ExtIEs F1AP-PROTOCOL-EXTENSION ::= {
	...
}

GBR-QoSFlowInformation::= SEQUENCE {
	maxFlowBitRateDownlink			BitRate,
	maxFlowBitRateUplink			BitRate,
	guaranteedFlowBitRateDownlink	BitRate,
	guaranteedFlowBitRateUplink		BitRate,
	maxPacketLossRateDownlink		MaxPacketLossRate		OPTIONAL,
	maxPacketLossRateUplink			MaxPacketLossRate		OPTIONAL,
	iE-Extensions					ProtocolExtensionContainer { { GBR-QosFlowInformation-ExtIEs} } OPTIONAL,
	...
}

GBR-QosFlowInformation-ExtIEs F1AP-PROTOCOL-EXTENSION ::= {
	{ 	ID id-AlternativeQoSParaSetList	CRITICALITY ignore	EXTENSION AlternativeQoSParaSetList	PRESENCE optional	},
	...
}

CG-Config ::= OCTET STRING

GeographicalCoordinates ::= SEQUENCE {
	tRPPositionDefinitionType	TRPPositionDefinitionType,
	dLPRSResourceCoordinates	DLPRSResourceCoordinates	OPTIONAL,
	iE-Extensions				ProtocolExtensionContainer { { GeographicalCoordinates-ExtIEs } } OPTIONAL
}

GeographicalCoordinates-ExtIEs F1AP-PROTOCOL-EXTENSION ::= {
	{ ID id-ARPLocationInfo		CRITICALITY ignore EXTENSION ARPLocationInformation	PRESENCE optional},
	...
}

GNB-CU-MBS-F1AP-ID		::= INTEGER (0..4294967295)

GNBCUMeasurementID ::= INTEGER (0.. 4095, ...)

GNBDUMeasurementID ::= INTEGER (0.. 4095, ...)

GNB-CUSystemInformation::= SEQUENCE {
	sibtypetobeupdatedlist	SEQUENCE (SIZE(1.. maxnoofSIBTypes)) OF SibtypetobeupdatedListItem,
	iE-Extensions					ProtocolExtensionContainer { { GNB-CUSystemInformation-ExtIEs} } OPTIONAL,
	...
}

GNB-CUSystemInformation-ExtIEs F1AP-PROTOCOL-EXTENSION ::= {
	{ID id-systemInformationAreaID  CRITICALITY ignore	EXTENSION SystemInformationAreaID PRESENCE optional},
	...
}

GNB-CU-TNL-Association-Setup-Item::= SEQUENCE {
	tNLAssociationTransportLayerAddress		CP-TransportLayerAddress	,
	iE-Extensions							ProtocolExtensionContainer { { GNB-CU-TNL-Association-Setup-Item-ExtIEs} } OPTIONAL
}

GNB-CU-TNL-Association-Setup-Item-ExtIEs F1AP-PROTOCOL-EXTENSION ::= {
	...
}

GNB-CU-TNL-Association-Failed-To-Setup-Item ::= SEQUENCE {
	tNLAssociationTransportLayerAddress		CP-TransportLayerAddress	,
	cause									Cause,
	iE-Extensions							ProtocolExtensionContainer { { GNB-CU-TNL-Association-Failed-To-Setup-Item-ExtIEs} } OPTIONAL
}

GNB-CU-TNL-Association-Failed-To-Setup-Item-ExtIEs F1AP-PROTOCOL-EXTENSION ::= {
	...
}


GNB-CU-TNL-Association-To-Add-Item ::= SEQUENCE {
	tNLAssociationTransportLayerAddress		CP-TransportLayerAddress	,
	tNLAssociationUsage						TNLAssociationUsage,
	iE-Extensions							ProtocolExtensionContainer { { GNB-CU-TNL-Association-To-Add-Item-ExtIEs} } OPTIONAL
}

GNB-CU-TNL-Association-To-Add-Item-ExtIEs F1AP-PROTOCOL-EXTENSION ::= {
	...
}

GNB-CU-TNL-Association-To-Remove-Item::= SEQUENCE {
	tNLAssociationTransportLayerAddress		CP-TransportLayerAddress	,
	iE-Extensions							ProtocolExtensionContainer { { GNB-CU-TNL-Association-To-Remove-Item-ExtIEs} } OPTIONAL
}

GNB-CU-TNL-Association-To-Remove-Item-ExtIEs F1AP-PROTOCOL-EXTENSION ::= {
	{ID id-TNLAssociationTransportLayerAddressgNBDU	CRITICALITY reject	EXTENSION CP-TransportLayerAddress	PRESENCE optional},
	...
}


GNB-CU-TNL-Association-To-Update-Item::= SEQUENCE {
	tNLAssociationTransportLayerAddress		CP-TransportLayerAddress	,
	tNLAssociationUsage						TNLAssociationUsage OPTIONAL,
	iE-Extensions							ProtocolExtensionContainer { { GNB-CU-TNL-Association-To-Update-Item-ExtIEs} } OPTIONAL
}

GNB-CU-TNL-Association-To-Update-Item-ExtIEs F1AP-PROTOCOL-EXTENSION ::= {
	...
}

GNB-CU-UE-F1AP-ID		::= INTEGER (0..4294967295)

GNB-DU-Cell-Resource-Configuration	::= SEQUENCE {
	subcarrierSpacing				SubcarrierSpacing,
	dUFTransmissionPeriodicity		DUFTransmissionPeriodicity	OPTIONAL,
	dUF-Slot-Config-List			DUF-Slot-Config-List	OPTIONAL,
	hSNATransmissionPeriodicity		HSNATransmissionPeriodicity,
	hsNSASlotConfigList				HSNASlotConfigList	OPTIONAL,
	iE-Extensions					ProtocolExtensionContainer { { GNB-DU-Cell-Resource-Configuration-ExtIEs } } OPTIONAL
}

GNB-DU-Cell-Resource-Configuration-ExtIEs F1AP-PROTOCOL-EXTENSION ::= {
	{ID id-rBSetConfiguration       CRITICALITY reject	EXTENSION       RBSetConfiguration	PRESENCE optional}|
	{ID id-frequency-Domain-HSNA-Configuration-List	 CRITICALITY reject	EXTENSION    Frequency-Domain-HSNA-Configuration-List   PRESENCE optional}|
	{ID id-child-IAB-Nodes-NA-Resource-List	CRITICALITY reject	EXTENSION Child-IAB-Nodes-NA-Resource-List    PRESENCE optional}|
	{ID id-Parent-IAB-Nodes-NA-Resource-Configuration-List   CRITICALITY reject	EXTENSION  Parent-IAB-Nodes-NA-Resource-Configuration-List  PRESENCE optional},
	...
}

GNB-DU-MBS-F1AP-ID		::= INTEGER (0..4294967295)


GNB-DU-UE-F1AP-ID		::= INTEGER (0..4294967295)

GNB-DU-ID			::= INTEGER (0..68719476735)

GNB-CU-Name ::= PrintableString(SIZE(1..150,...))

GNB-DU-Name ::= PrintableString(SIZE(1..150,...))

Extended-GNB-CU-Name	 ::= SEQUENCE {
	gNB-CU-NameVisibleString		GNB-CU-NameVisibleString					OPTIONAL,
	gNB-CU-NameUTF8String			GNB-CU-NameUTF8String						OPTIONAL,
	iE-Extensions					ProtocolExtensionContainer { { Extended-GNB-CU-Name-ExtIEs } } OPTIONAL,
	...
}

Extended-GNB-CU-Name-ExtIEs F1AP-PROTOCOL-EXTENSION ::= {
	...
}

GNB-CU-NameVisibleString ::= VisibleString(SIZE(1..150,...))

GNB-CU-NameUTF8String ::= UTF8String(SIZE(1..150,...))

Extended-GNB-DU-Name	 ::= SEQUENCE {
	gNB-DU-NameVisibleString		GNB-DU-NameVisibleString					OPTIONAL,
	gNB-DU-NameUTF8String			GNB-DU-NameUTF8String						OPTIONAL,
	iE-Extensions					ProtocolExtensionContainer { { Extended-GNB-DU-Name-ExtIEs } } OPTIONAL,
	...
}

Extended-GNB-DU-Name-ExtIEs F1AP-PROTOCOL-EXTENSION ::= {
	...
}

GNB-DU-NameVisibleString ::= VisibleString(SIZE(1..150,...))

GNB-DU-NameUTF8String ::= UTF8String(SIZE(1..150,...))


GNB-DU-Served-Cells-Item ::= SEQUENCE {
	served-Cell-Information		Served-Cell-Information,
	gNB-DU-System-Information	GNB-DU-System-Information	OPTIONAL,
	iE-Extensions				ProtocolExtensionContainer { { GNB-DU-Served-Cells-ItemExtIEs} }	OPTIONAL,
	...
}

GNB-DU-Served-Cells-ItemExtIEs 	F1AP-PROTOCOL-EXTENSION ::= {
	...
}

GNB-DU-System-Information ::= SEQUENCE {
	mIB-message		MIB-message,
	sIB1-message		SIB1-message,
	iE-Extensions					ProtocolExtensionContainer { { GNB-DU-System-Information-ExtIEs } } OPTIONAL,
	...
}

GNB-DU-System-Information-ExtIEs F1AP-PROTOCOL-EXTENSION ::= {
	{ ID id-SIB12-message		CRITICALITY ignore	EXTENSION SIB12-message		PRESENCE optional}|
	{ ID id-SIB13-message		CRITICALITY ignore	EXTENSION SIB13-message		PRESENCE optional}|
	{ ID id-SIB14-message		CRITICALITY ignore	EXTENSION SIB14-message		PRESENCE optional}|
	{ ID id-SIB10-message		CRITICALITY ignore	EXTENSION SIB10-message		PRESENCE optional}|
	{ ID id-SIB17-message		CRITICALITY ignore	EXTENSION SIB17-message		PRESENCE optional}|
	{ ID id-SIB20-message		CRITICALITY ignore	EXTENSION SIB20-message		PRESENCE optional}|
	{ ID id-SIB15-message		CRITICALITY ignore	EXTENSION SIB15-message		PRESENCE optional},
	...
}

GNB-DUConfigurationQuery ::= ENUMERATED {true, ...}

GNBDUOverloadInformation ::= ENUMERATED {overloaded, not-overloaded}

GNB-DU-TNL-Association-To-Remove-Item::= SEQUENCE {
	tNLAssociationTransportLayerAddress				CP-TransportLayerAddress	,
	tNLAssociationTransportLayerAddressgNBCU		CP-TransportLayerAddress		OPTIONAL,
	iE-Extensions									ProtocolExtensionContainer { { GNB-DU-TNL-Association-To-Remove-Item-ExtIEs} } OPTIONAL
}

GNB-DU-TNL-Association-To-Remove-Item-ExtIEs F1AP-PROTOCOL-EXTENSION ::= {
	...
}

GNBDUUESliceMaximumBitRateList::= SEQUENCE (SIZE(1.. maxnoofSMBRValues)) OF GNBDUUESliceMaximumBitRateItem

GNBDUUESliceMaximumBitRateItem::= SEQUENCE {
	sNSSAI		SNSSAI,
	uESliceMaximumBitRateUL		BitRate,
	iE-Extensions				ProtocolExtensionContainer { { GNBDUUESliceMaximumBitRateItem-ExtIEs} } OPTIONAL,
	...
}

GNBDUUESliceMaximumBitRateItem-ExtIEs F1AP-PROTOCOL-EXTENSION ::= {
	...
}

GNB-RxTxTimeDiff ::= SEQUENCE {
	rxTxTimeDiff			GNBRxTxTimeDiffMeas,
	additionalPath-List		AdditionalPath-List		OPTIONAL,
	iE-Extensions			ProtocolExtensionContainer { { GNB-RxTxTimeDiff-ExtIEs} }  OPTIONAL
}

GNB-RxTxTimeDiff-ExtIEs F1AP-PROTOCOL-EXTENSION ::= {
	{ ID id-ExtendedAdditionalPathList		CRITICALITY ignore EXTENSION ExtendedAdditionalPathList 	PRESENCE optional}|
	{ ID id-TRPTEGInformation				CRITICALITY ignore EXTENSION TRPTEGInformation			PRESENCE optional },
	...
}

GNBRxTxTimeDiffMeas ::= CHOICE {
	k0			INTEGER (0.. 1970049),
	k1			INTEGER (0.. 985025),
	k2			INTEGER (0.. 492513),
	k3			INTEGER (0.. 246257),
	k4			INTEGER (0.. 123129),
	k5			INTEGER (0.. 61565),
	choice-extension		ProtocolIE-SingleContainer { { GNBRxTxTimeDiffMeas-ExtIEs } }
}

GNBRxTxTimeDiffMeas-ExtIEs		F1AP-PROTOCOL-IES ::= {
	...
}

GNBSetID ::= BIT STRING (SIZE(22))

GTP-TEID				::= OCTET STRING (SIZE (4))

GTPTLAs	::= SEQUENCE (SIZE(1.. maxnoofGTPTLAs)) OF	GTPTLA-Item


GTPTLA-Item	::= SEQUENCE {
	gTPTransportLayerAddress				TransportLayerAddress,
	iE-Extensions	ProtocolExtensionContainer { { GTPTLA-Item-ExtIEs } }			OPTIONAL
}

GTPTLA-Item-ExtIEs F1AP-PROTOCOL-EXTENSION ::= {
	...
}

GTPTunnel				::= SEQUENCE {
	transportLayerAddress		TransportLayerAddress,
	gTP-TEID		GTP-TEID,
	iE-Extensions				ProtocolExtensionContainer { { GTPTunnel-ExtIEs } } OPTIONAL,
	...
}

GTPTunnel-ExtIEs F1AP-PROTOCOL-EXTENSION ::= {
	...
}

-- H

HandoverPreparationInformation ::= OCTET STRING

HardwareLoadIndicator ::= SEQUENCE {
	dLHardwareLoadIndicator			INTEGER (0..100, ...),
	uLHardwareLoadIndicator			INTEGER (0..100, ...),
	iE-Extensions					ProtocolExtensionContainer { { HardwareLoadIndicator-ExtIEs } } 	OPTIONAL,
	...
}

HardwareLoadIndicator-ExtIEs	F1AP-PROTOCOL-EXTENSION ::= {
	...
}

HSNASlotConfigList ::= SEQUENCE (SIZE(1..maxnoofHSNASlots)) OF HSNASlotConfigItem

HSNASlotConfigItem 	::=	SEQUENCE {
	hSNADownlink			HSNADownlink 		OPTIONAL,
	hSNAUplink				HSNAUplink 			OPTIONAL,
	hSNAFlexible			HSNAFlexible 		OPTIONAL,
	iE-Extensions			ProtocolExtensionContainer { { HSNASlotConfigItem-ExtIEs } } OPTIONAL
}

HSNASlotConfigItem-ExtIEs F1AP-PROTOCOL-EXTENSION ::= {
	...
}
HSNADownlink ::= ENUMERATED { hard, soft, notavailable }

HSNAFlexible ::= ENUMERATED { hard, soft, notavailable }

HSNAUplink ::= ENUMERATED { hard, soft, notavailable }

HSNATransmissionPeriodicity ::=	ENUMERATED { ms0p5, ms0p625, ms1, ms1p25, ms2, ms2p5, ms5, ms10, ms20, ms40, ms80, ms160, ...}

-- I

IAB-Barred	::=	ENUMERATED {barred, not-barred, ...}

IABConditionalRRCMessageDeliveryIndication ::= ENUMERATED {true, ...}

IABCongestionIndication ::= SEQUENCE {
	iAB-Congestion-Indication-List			IAB-Congestion-Indication-List,
	iE-Extensions	ProtocolExtensionContainer { { IAB-Congestion-Indication-List-ExtIEs } } OPTIONAL
}

IAB-Congestion-Indication-List-ExtIEs	F1AP-PROTOCOL-EXTENSION ::= {
	...
}

IAB-Congestion-Indication-List ::= SEQUENCE (SIZE(1..maxnoofIABCongInd)) OF IAB-Congestion-Indication-Item

IAB-Congestion-Indication-Item ::= SEQUENCE {
	childNodeIdentifier				BAPAddress,
    bHRLCCHList		                BHRLCCHList	    OPTIONAL,
	iE-Extensions					ProtocolExtensionContainer { { IAB-Congestion-Indication-ItemExtIEs } }	OPTIONAL
}

IAB-Congestion-Indication-ItemExtIEs F1AP-PROTOCOL-EXTENSION ::= {
	...
}


IAB-Info-IAB-donor-CU ::=	SEQUENCE{
	iAB-STC-Info	IAB-STC-Info	OPTIONAL,
	iE-Extensions					ProtocolExtensionContainer { { IAB-Info-IAB-donor-CU-ExtIEs } } OPTIONAL
}

IAB-Info-IAB-donor-CU-ExtIEs F1AP-PROTOCOL-EXTENSION ::= {
	...
}

IAB-Info-IAB-DU ::=	SEQUENCE{
	multiplexingInfo		MultiplexingInfo	OPTIONAL,
	iAB-STC-Info		IAB-STC-Info	OPTIONAL,
	iE-Extensions						ProtocolExtensionContainer { { IAB-Info-IAB-DU-ExtIEs } } OPTIONAL
}

IAB-Info-IAB-DU-ExtIEs F1AP-PROTOCOL-EXTENSION ::= {
	...
}

IAB-MT-Cell-List ::= SEQUENCE (SIZE(1..maxnoofServingCells)) OF IAB-MT-Cell-List-Item

IAB-MT-Cell-List-Item ::= 	SEQUENCE {
	nRCellIdentity				NRCellIdentity,
	dU-RX-MT-RX					DU-RX-MT-RX,
	dU-TX-MT-TX					DU-TX-MT-TX,
	dU-RX-MT-TX					DU-RX-MT-TX,
	dU-TX-MT-RX					DU-TX-MT-RX,
	iE-Extensions				ProtocolExtensionContainer { { IAB-MT-Cell-List-Item-ExtIEs } } OPTIONAL
}

IAB-MT-Cell-List-Item-ExtIEs F1AP-PROTOCOL-EXTENSION ::= {
	{ ID id-DU-RX-MT-RX-Extend			CRITICALITY ignore	EXTENSION DU-RX-MT-RX-Extend	PRESENCE optional	}|
	{ ID id-DU-TX-MT-TX-Extend			CRITICALITY ignore	EXTENSION DU-TX-MT-TX-Extend	PRESENCE optional	}|
	{ ID id-DU-RX-MT-TX-Extend			CRITICALITY ignore	EXTENSION DU-RX-MT-TX-Extend	PRESENCE optional	}|
	{ ID id-DU-TX-MT-RX-Extend			CRITICALITY ignore	EXTENSION DU-TX-MT-RX-Extend	PRESENCE optional	},
	...
}



IAB-MT-Cell-NA-Resource-Configuration-Mode-Info	::=	CHOICE {
	fDD		IAB-MT-Cell-NA-Resource-Configuration-FDD-Info,
	tDD		IAB-MT-Cell-NA-Resource-Configuration-TDD-Info,
	choice-extension			ProtocolIE-SingleContainer { { IAB-MT-Cell-NA-Resource-Configuration-Mode-Info-ExtIEs} }
}

IAB-MT-Cell-NA-Resource-Configuration-Mode-Info-ExtIEs F1AP-PROTOCOL-IES ::= {
	...
}

IAB-MT-Cell-NA-Resource-Configuration-FDD-Info ::= SEQUENCE {
	gNB-DU-Cell-NA-Resource-Configuration-FDD-UL				GNB-DU-Cell-Resource-Configuration,
	gNB-DU-Cell-NA-Resource-Configuration-FDD-DL				GNB-DU-Cell-Resource-Configuration,
	uL-FreqInfo							NRFreqInfo					OPTIONAL,
	uL-Transmission-Bandwidth			Transmission-Bandwidth		OPTIONAL,
	uL-NR-Carrier-List  				NRCarrierList				OPTIONAL,
	dL-FreqInfo							NRFreqInfo					OPTIONAL,
	dL-Transmission-Bandwidth			Transmission-Bandwidth		OPTIONAL,
	dL-NR-Carrier-List  				NRCarrierList				OPTIONAL,
	iE-Extensions						ProtocolExtensionContainer { {IAB-MT-Cell-NA-Resource-Configuration-FDD-Info-ExtIEs} } OPTIONAL,
	...
}

IAB-MT-Cell-NA-Resource-Configuration-FDD-Info-ExtIEs F1AP-PROTOCOL-EXTENSION ::= {
	...
}

IAB-MT-Cell-NA-Resource-Configuration-TDD-Info ::= SEQUENCE {
	gNB-DU-Cell-NA-Resourc-Configuration-TDD				GNB-DU-Cell-Resource-Configuration,
	nRFreqInfo							NRFreqInfo  	OPTIONAL,
	transmission-Bandwidth			    Transmission-Bandwidth  	  OPTIONAL,
	nR-Carrier-List   		  	        NRCarrierList  	OPTIONAL,
	iE-Extensions					    ProtocolExtensionContainer { {IAB-MT-Cell-NA-Resource-Configuration-TDD-Info-ExtIEs} } OPTIONAL,
	...
}

IAB-MT-Cell-NA-Resource-Configuration-TDD-Info-ExtIEs F1AP-PROTOCOL-EXTENSION ::= {
	...
}

IAB-STC-Info	::=	SEQUENCE{
	iAB-STC-Info-List	IAB-STC-Info-List,
	iE-Extensions		ProtocolExtensionContainer { { IAB-STC-Info-ExtIEs } } OPTIONAL
}

IAB-STC-Info-ExtIEs F1AP-PROTOCOL-EXTENSION ::= {
	...
}

IAB-STC-Info-List ::= 	SEQUENCE (SIZE(1..maxnoofIABSTCInfo)) OF IAB-STC-Info-Item

IAB-STC-Info-Item::=	SEQUENCE {
	sSB-freqInfo						SSB-freqInfo,
	sSB-subcarrierSpacing				SSB-subcarrierSpacing,
	sSB-transmissionPeriodicity			SSB-transmissionPeriodicity,
	sSB-transmissionTimingOffset		SSB-transmissionTimingOffset,
	sSB-transmissionBitmap				SSB-transmissionBitmap,
	iE-Extensions		ProtocolExtensionContainer { { IAB-STC-Info-Item-ExtIEs } } OPTIONAL
}

IAB-STC-Info-Item-ExtIEs F1AP-PROTOCOL-EXTENSION ::= {
	...
}

IAB-Allocated-TNL-Address-Item	::= SEQUENCE {
	iABTNLAddress				IABTNLAddress,
	iABTNLAddressUsage			IABTNLAddressUsage	 	OPTIONAL,
	iE-Extensions				ProtocolExtensionContainer { { IAB-Allocated-TNL-Address-Item-ExtIEs } } OPTIONAL
}

IAB-Allocated-TNL-Address-Item-ExtIEs F1AP-PROTOCOL-EXTENSION ::= {
	...
}

IAB-DU-Cell-Resource-Configuration-Mode-Info	::=	CHOICE {
	fDD		IAB-DU-Cell-Resource-Configuration-FDD-Info,
	tDD		IAB-DU-Cell-Resource-Configuration-TDD-Info,
	choice-extension			ProtocolIE-SingleContainer { { IAB-DU-Cell-Resource-Configuration-Mode-Info-ExtIEs} }
}

IAB-DU-Cell-Resource-Configuration-Mode-Info-ExtIEs F1AP-PROTOCOL-IES ::= {
	...
}

IAB-DU-Cell-Resource-Configuration-FDD-Info ::= SEQUENCE {
	gNB-DU-Cell-Resource-Configuration-FDD-UL				GNB-DU-Cell-Resource-Configuration,
	gNB-DU-Cell-Resource-Configuration-FDD-DL				GNB-DU-Cell-Resource-Configuration,
	iE-Extensions					ProtocolExtensionContainer { {IAB-DU-Cell-Resource-Configuration-FDD-Info-ExtIEs} } OPTIONAL,
	...
}

IAB-DU-Cell-Resource-Configuration-FDD-Info-ExtIEs F1AP-PROTOCOL-EXTENSION ::= {
	{ID id-uL-FreqInfo					CRITICALITY reject	EXTENSION	NRFreqInfo					PRESENCE optional}|
	{ID id-uL-Transmission-Bandwidth	CRITICALITY reject	EXTENSION	Transmission-Bandwidth		PRESENCE optional}|
	{ID id-uL-NR-Carrier-List			CRITICALITY reject	EXTENSION	NRCarrierList				PRESENCE optional}|
	{ID id-dL-FreqInfo					CRITICALITY reject	EXTENSION	NRFreqInfo  				PRESENCE optional}|
	{ID id-dL-Transmission-Bandwidth	CRITICALITY reject	EXTENSION	Transmission-Bandwidth		PRESENCE optional}|
	{ID id-dL-NR-Carrier-List			CRITICALITY reject	EXTENSION	NRCarrierList				PRESENCE optional},
	...
}

IAB-DU-Cell-Resource-Configuration-TDD-Info ::= SEQUENCE {
	gNB-DU-Cell-Resourc-Configuration-TDD				GNB-DU-Cell-Resource-Configuration,
	iE-Extensions					ProtocolExtensionContainer { {IAB-DU-Cell-Resource-Configuration-TDD-Info-ExtIEs} } OPTIONAL,
	...
}

IAB-DU-Cell-Resource-Configuration-TDD-Info-ExtIEs F1AP-PROTOCOL-EXTENSION ::= {
	{ID id-nRFreqInfo				CRITICALITY reject	EXTENSION  NRFreqInfo  				PRESENCE optional}|
	{ID id-transmission-Bandwidth	CRITICALITY reject	EXTENSION  Transmission-Bandwidth  	PRESENCE optional}|
	{ID id-nR-Carrier-List			CRITICALITY reject	EXTENSION  NRCarrierList  			PRESENCE optional},
	...
}

IABIPv6RequestType	 ::= CHOICE {
	iPv6Address						IABTNLAddressesRequested,
	iPv6Prefix						IABTNLAddressesRequested,
	choice-extension				ProtocolIE-SingleContainer { { IABIPv6RequestType-ExtIEs} }
}

IABIPv6RequestType-ExtIEs F1AP-PROTOCOL-IES ::= {
	...
}

IABTNLAddress ::= CHOICE {
	iPv4Address						BIT STRING (SIZE(32)),
	iPv6Address						BIT STRING (SIZE(128)),
	iPv6Prefix						BIT STRING (SIZE(64)),
	choice-extension				ProtocolIE-SingleContainer { { IABTNLAddress-ExtIEs} }
}

IABTNLAddress-ExtIEs F1AP-PROTOCOL-IES ::= {
	...
}

IABTNLAddressesRequested ::= SEQUENCE {
	tNLAddressesOrPrefixesRequestedAllTraffic	INTEGER (1..256) 	OPTIONAL,
	tNLAddressesOrPrefixesRequestedF1-C			INTEGER (1..256) 	OPTIONAL,
	tNLAddressesOrPrefixesRequestedF1-U			INTEGER (1..256) 	OPTIONAL,
	tNLAddressesOrPrefixesRequestedNoNF1		INTEGER (1..256) 	OPTIONAL,
	iE-Extensions		ProtocolExtensionContainer { { IABTNLAddressesRequested-ExtIEs } } OPTIONAL
}

IABTNLAddressesRequested-ExtIEs F1AP-PROTOCOL-EXTENSION ::= {
	...
}

IAB-TNL-Addresses-To-Remove-Item ::= SEQUENCE {
	iABTNLAddress			IABTNLAddress,
	iE-Extensions			ProtocolExtensionContainer { { IAB-TNL-Addresses-To-Remove-Item-ExtIEs} } OPTIONAL
}

IAB-TNL-Addresses-To-Remove-Item-ExtIEs F1AP-PROTOCOL-EXTENSION ::= {
	...
}

IAB-TNL-Addresses-Exception ::= 	SEQUENCE {
	iABTNLAddressList			IABTNLAddressList,
	iE-Extensions				ProtocolExtensionContainer { { IAB-TNL-Addresses-Exception-ExtIEs} } OPTIONAL
}

IAB-TNL-Addresses-Exception-ExtIEs F1AP-PROTOCOL-EXTENSION ::= {
	...
}

IABTNLAddressList ::= SEQUENCE (SIZE(1.. maxnoofTLAsIAB)) OF IABTNLAddress-Item

IABTNLAddress-Item ::= SEQUENCE {
	iABTNLAddress		IABTNLAddress	,
	iE-Extensions	ProtocolExtensionContainer { { IABTNLAddress-ItemExtIEs } }	OPTIONAL
}

IABTNLAddress-ItemExtIEs 	F1AP-PROTOCOL-EXTENSION ::= {
	...
}

IABTNLAddressUsage ::= ENUMERATED {
	f1-c,
	f1-u,
	non-f1,
	...
}


IABv4AddressesRequested ::= SEQUENCE {
	iABv4AddressesRequested			IABTNLAddressesRequested,
	iE-Extensions		ProtocolExtensionContainer { { IABv4AddressesRequested-ExtIEs} } OPTIONAL
}

IABv4AddressesRequested-ExtIEs F1AP-PROTOCOL-EXTENSION ::= {
	...
}

ImplicitFormat	::= SEQUENCE	{
	dUFSlotformatIndex 			DUFSlotformatIndex,
	iE-Extensions		ProtocolExtensionContainer { { ImplicitFormat-ExtIEs } } OPTIONAL
}

ImplicitFormat-ExtIEs F1AP-PROTOCOL-EXTENSION ::= {
	...
}

IgnorePRACHConfiguration::= ENUMERATED { true,...}

IgnoreResourceCoordinationContainer ::= ENUMERATED { yes,...}
InactivityMonitoringRequest ::= ENUMERATED { true,...}
InactivityMonitoringResponse ::= ENUMERATED { not-supported,...}
InterfacesToTrace ::= BIT STRING (SIZE(8))

IntendedTDD-DL-ULConfig ::= SEQUENCE {
	nRSCS						ENUMERATED { scs15, scs30, scs60, scs120,..., scs480, scs960},
	nRCP						ENUMERATED { normal, extended,...},
	nRDLULTxPeriodicity			ENUMERATED { ms0p5, ms0p625, ms1, ms1p25, ms2, ms2p5, ms3, ms4, ms5, ms10, ms20, ms40, ms60, ms80, ms100, ms120, ms140, ms160, ...},
	slot-Configuration-List 	Slot-Configuration-List,
	iE-Extensions						ProtocolExtensionContainer { {IntendedTDD-DL-ULConfig-ExtIEs} } OPTIONAL
}

InterFrequencyConfig-NoGap ::= ENUMERATED {
	true,
	...
}

IngressNonF1terminatingTopologyIndicator ::= ENUMERATED {true, ...}

IntendedTDD-DL-ULConfig-ExtIEs 	F1AP-PROTOCOL-EXTENSION ::= {
	...
}

IPHeaderInformation ::= SEQUENCE {
	destinationIABTNLAddress			IABTNLAddress,
	dsInformationList					DSInformationList	OPTIONAL,
	iPv6FlowLabel						BIT STRING (SIZE (20))	OPTIONAL,
	iE-Extensions						ProtocolExtensionContainer { { IPHeaderInformation-ItemExtIEs} } OPTIONAL,
	...
}

IPHeaderInformation-ItemExtIEs F1AP-PROTOCOL-EXTENSION ::= {
	...
}

IPtolayer2TrafficMappingInfo ::= SEQUENCE {
	iPtolayer2TrafficMappingInfoToAdd					IPtolayer2TrafficMappingInfoList		OPTIONAL,
	iPtolayer2TrafficMappingInfoToRemove				MappingInformationtoRemove				OPTIONAL,
	iE-Extensions										ProtocolExtensionContainer { { IPtolayer2TrafficMappingInfo-ItemExtIEs} } OPTIONAL,
	...
}

IPtolayer2TrafficMappingInfoList ::= SEQUENCE (SIZE(1..maxnoofMappingEntries)) OF IPtolayer2TrafficMappingInfo-Item

IPtolayer2TrafficMappingInfo-Item ::= SEQUENCE {
	mappingInformationIndex		MappingInformationIndex,
	iPHeaderInformation			IPHeaderInformation,
	bHInfo	 					BHInfo,	iE-Extensions				ProtocolExtensionContainer { { IPtolayer2TrafficMappingInfo-ItemExtIEs} } OPTIONAL,
	...
}

IPtolayer2TrafficMappingInfo-ItemExtIEs F1AP-PROTOCOL-EXTENSION ::= {
	...
}

-- J

-- K

-- L

L139Info ::= SEQUENCE {
	prachSCS						ENUMERATED {scs15, scs30, scs60, scs120, ..., scs480, scs960},
	rootSequenceIndex			INTEGER (0..137)								OPTIONAL,
	iE-Extension				ProtocolExtensionContainer { {L139Info-ExtIEs} } 		OPTIONAL,
	...
}

L139Info-ExtIEs F1AP-PROTOCOL-EXTENSION ::= {
	...
}

L839Info ::= SEQUENCE {
	rootSequenceIndex			INTEGER (0..837),
	restrictedSetConfig			ENUMERATED {unrestrictedSet, restrictedSetTypeA,
											restrictedSetTypeB, ...},
	iE-Extension		ProtocolExtensionContainer { {L839Info-ExtIEs} } 		OPTIONAL,
	...
}

L839Info-ExtIEs F1AP-PROTOCOL-EXTENSION ::= {
	...
}

L571Info ::= SEQUENCE {
	prachSCSForL571				ENUMERATED { scs30, scs120, ... , scs480},
	rootSequenceIndex			INTEGER (0..569),
	iE-Extension				ProtocolExtensionContainer { {L571Info-ExtIEs} } 		OPTIONAL,
	...
}

L571Info-ExtIEs F1AP-PROTOCOL-EXTENSION ::= {
	...
}

L1151Info ::= SEQUENCE {
	prachSCSForL1151				ENUMERATED { scs15, scs120,...},
	rootSequenceIndex				INTEGER (0..1149),
	iE-Extension					ProtocolExtensionContainer { {L1151Info-ExtIEs} } 		OPTIONAL,
	...
}

L1151Info-ExtIEs F1AP-PROTOCOL-EXTENSION ::= {
	...
}


LastUsedCellIndication ::= ENUMERATED {true, ...}

LCID ::= INTEGER (1..32, ...)


LCS-to-GCS-Translation::= SEQUENCE {
	alpha				INTEGER (0..3599),
	beta				INTEGER (0..3599),
	gamma				INTEGER (0..3599),
	iE-Extensions		ProtocolExtensionContainer { { LCS-to-GCS-Translation-ExtIEs} } OPTIONAL,
	...
}

LCS-to-GCS-Translation-ExtIEs F1AP-PROTOCOL-EXTENSION ::= {
	...
}

LCStoGCSTranslationList ::= SEQUENCE (SIZE (1.. maxnooflcs-gcs-translation)) OF LCStoGCSTranslation

LCStoGCSTranslation ::= SEQUENCE {
	alpha			INTEGER (0..359),
	alpha-fine		INTEGER (0..9)		OPTIONAL,
	beta			INTEGER (0..359),
	beta-fine		INTEGER (0..9)		OPTIONAL,
	gamma			INTEGER (0..359),
	gamma-fine		INTEGER (0..9)		OPTIONAL,
	iE-Extensions				ProtocolExtensionContainer { {LCStoGCSTranslation-ExtIEs} } OPTIONAL
}

LCStoGCSTranslation-ExtIEs F1AP-PROTOCOL-EXTENSION ::= {
	...
}

LMF-MeasurementID ::= INTEGER (1.. 65536, ...)

LMF-UE-MeasurementID ::= INTEGER (1.. 256, ...)

LocationDependentMBSF1UInformation ::= SEQUENCE (SIZE(1..maxnoofMBSAreaSessionIDs)) OF LocationDependentMBSF1UInformation-Item
LocationDependentMBSF1UInformation-Item ::= SEQUENCE {
	mbsAreaSession-ID				MBS-Area-Session-ID,
	mbs-f1u-info-at-CU				UPTransportLayerInformation,
	iE-Extensions					ProtocolExtensionContainer	{ { LocationDependentMBSF1UInformation-Item-ExtIEs } }	OPTIONAL,
	...
}

LocationDependentMBSF1UInformation-Item-ExtIEs		F1AP-PROTOCOL-EXTENSION ::= {
	...
}

LocationMeasurementInformation ::= OCTET STRING

LocationUncertainty ::= SEQUENCE {
	horizontalUncertainty		INTEGER (0..255),
	horizontalConfidence		INTEGER (0..100),
	verticalUncertainty			INTEGER (0..255),
	verticalConfidence			INTEGER (0..100),
	iE-Extensions				ProtocolExtensionContainer { { LocationUncertainty-ExtIEs} } OPTIONAL
}

LocationUncertainty-ExtIEs F1AP-PROTOCOL-EXTENSION ::= {
	...
}

LongDRXCycleLength ::= 	ENUMERATED
{ms10, ms20, ms32, ms40, ms60, ms64, ms70, ms80, ms128, ms160, ms256, ms320, ms512, ms640, ms1024, ms1280, ms2048, ms2560, ms5120, ms10240, ...}

LowerLayerPresenceStatusChange ::= ENUMERATED {
	suspend-lower-layers,
	resume-lower-layers,
	...

}

LoS-NLoSIndicatorHard ::= ENUMERATED {nLoS, loS}

LoS-NLoSIndicatorSoft ::= INTEGER (0..10)

LoS-NLoSInformation ::= CHOICE {
	loS-NLoSIndicatorSoft		LoS-NLoSIndicatorSoft,
	loS-NLoSIndicatorHard		LoS-NLoSIndicatorHard,
	choice-Extension			ProtocolIE-SingleContainer {{ LoS-NLoSInformation-ExtIEs}}
}

LoS-NLoSInformation-ExtIEs F1AP-PROTOCOL-IES ::= {
	...
}

LTEUESidelinkAggregateMaximumBitrate ::= SEQUENCE {
	uELTESidelinkAggregateMaximumBitrate		BitRate,
	iE-Extensions					ProtocolExtensionContainer { {LTEUESidelinkAggregateMaximumBitrate-ExtIEs} } OPTIONAL
}

LTEUESidelinkAggregateMaximumBitrate-ExtIEs F1AP-PROTOCOL-EXTENSION ::= {
	...
}

LTEV2XServicesAuthorized ::= SEQUENCE {
	vehicleUE			VehicleUE														OPTIONAL,
	pedestrianUE 		PedestrianUE													OPTIONAL,
	iE-Extensions		ProtocolExtensionContainer { {LTEV2XServicesAuthorized-ExtIEs} }		OPTIONAL
}

LTEV2XServicesAuthorized-ExtIEs F1AP-PROTOCOL-EXTENSION ::= {
	...
}

-- M

MappingInformationIndex	::= BIT STRING (SIZE (26))

MappingInformationtoRemove	::= SEQUENCE (SIZE(1..maxnoofMappingEntries)) OF MappingInformationIndex

MaskedIMEISV ::= 	BIT STRING (SIZE (64))

MaxDataBurstVolume  ::= INTEGER (0..4095, ..., 4096.. 2000000)
MaxPacketLossRate ::= INTEGER (0..1000)

MBS-Broadcast-NeighbourCellList ::= OCTET STRING

MBS-Flows-Mapped-To-MRB-List	::=	SEQUENCE (SIZE(1.. maxnoofMBSQoSFlows)) OF MBS-Flows-Mapped-To-MRB-Item

MBS-Flows-Mapped-To-MRB-Item 	::= SEQUENCE {
	mBS-QoSFlowIdentifier						QoSFlowIdentifier,
	mbs-QoSFlowLevelQoSParameters				QoSFlowLevelQoSParameters,
	iE-Extensions								ProtocolExtensionContainer { { MBS-Flows-Mapped-To-MRB-Item-ExtIEs} } OPTIONAL
}

MBS-Flows-Mapped-To-MRB-Item-ExtIEs 	F1AP-PROTOCOL-EXTENSION ::= {
	...
}


MBSF1UInformation ::= SEQUENCE {
	mbs-f1u-info				UPTransportLayerInformation,
	iE-Extensions					ProtocolExtensionContainer	{ { MBSF1UInformation-ExtIEs } }	OPTIONAL,
	...
}

MBSF1UInformation-ExtIEs		F1AP-PROTOCOL-EXTENSION ::= {
	...
}

MBSInterestIndication ::= OCTET STRING

MBS-Session-ID ::= SEQUENCE {
	tMGI						TMGI,
	nID							NID					OPTIONAL,
	iE-Extensions				ProtocolExtensionContainer { { MBS-Session-ID-ExtIEs} } OPTIONAL,
	...
}

MBS-Session-ID-ExtIEs F1AP-PROTOCOL-EXTENSION ::= {
	...
}

MBS-Area-Session-ID  ::= INTEGER (0..65535, ...)


MBS-CUtoDURRCInformation		::= SEQUENCE {
	mBS-Broadcast-Cell-List		MBS-Broadcast-Cell-List,
	mBS-Broadcast-MRB-List		MBS-Broadcast-MRB-List,
	iE-Extensions				ProtocolExtensionContainer { { MBS-CUtoDURRCInformation-ExtIEs } } OPTIONAL,
	...
}

MBS-CUtoDURRCInformation-ExtIEs F1AP-PROTOCOL-EXTENSION ::= {
	...
}

MBS-Broadcast-Cell-List	::= SEQUENCE (SIZE(1.. maxCellingNBDU))	OF  MBS-Broadcast-Cell-Item

MBS-Broadcast-Cell-Item ::= SEQUENCE {
	nRCGI						NRCGI,
	mtch-neighbourCell			OCTET STRING		OPTIONAL,
	iE-Extensions				ProtocolExtensionContainer { { MBS-Broadcast-Cell-Item-ExtIEs} } OPTIONAL,
	...
}

MBS-Broadcast-Cell-Item-ExtIEs F1AP-PROTOCOL-EXTENSION ::= {
	...
}

MBS-Broadcast-MRB-List	::= SEQUENCE (SIZE(1.. maxnoofMRBs))	OF  MBS-Broadcast-MRB-Item

MBS-Broadcast-MRB-Item ::= SEQUENCE {
	mRB-ID						MRB-ID,
	mRB-PDCP-Config-Broadcast	OCTET STRING,
	iE-Extensions				ProtocolExtensionContainer { { MBS-Broadcast-MRB-Item-ExtIEs} } OPTIONAL,
	...
}

MBS-Broadcast-MRB-Item-ExtIEs F1AP-PROTOCOL-EXTENSION ::= {
	...
}

MBSMulticastF1UContextDescriptor ::= SEQUENCE {
	multicastF1UContextReferenceF1		MulticastF1UContextReferenceF1,
	mc-F1UCtxtusage 	ENUMERATED {ptm, ptp, ptp-retransmission, ptp-forwarding, ...},
	mbsAreaSession						MBS-Area-Session-ID				OPTIONAL,
	iE-Extensions		ProtocolExtensionContainer	{{MBSMulticastF1UContextDescriptor-ExtIEs}} OPTIONAL,
	...
}

MBSMulticastF1UContextDescriptor-ExtIEs F1AP-PROTOCOL-EXTENSION ::= {
	...
}



MulticastF1UContext-ToBeSetup-Item ::= SEQUENCE {
   mRB-ID                  MRB-ID,
   mbs-f1u-info-at-DU      UPTransportLayerInformation,
   mbsProgressInformation		MRB-ProgressInformation						OPTIONAL,
   iE-Extensions           ProtocolExtensionContainer { {MulticastF1UContext-ToBeSetup-Item-ExtIEs} }	OPTIONAL,
	...
}

MulticastF1UContext-ToBeSetup-Item-ExtIEs F1AP-PROTOCOL-EXTENSION ::= {
	...
}

MulticastF1UContext-Setup-Item ::= SEQUENCE {
   mRB-ID                  MRB-ID,
   mbs-f1u-info-at-CU      UPTransportLayerInformation,
   iE-Extensions           ProtocolExtensionContainer { {MulticastF1UContext-Setup-Item-ExtIEs} }	OPTIONAL,
	...
}

MulticastF1UContext-Setup-Item-ExtIEs F1AP-PROTOCOL-EXTENSION ::= {
	...
}


MulticastF1UContext-FailedToBeSetup-Item ::= SEQUENCE {
	mRB-ID						MRB-ID,
	cause						Cause							OPTIONAL,
   iE-Extensions           ProtocolExtensionContainer { {MulticastF1UContext-FailedToBeSetup-Item-ExtIEs} }	OPTIONAL,
	...
}

MulticastF1UContext-FailedToBeSetup-Item-ExtIEs F1AP-PROTOCOL-EXTENSION ::= {
	...
}



MBSPTPRetransmissionTunnelRequired ::= ENUMERATED {true,	...}


MBS-ServiceArea ::= CHOICE {
	locationindependent		MBS-ServiceAreaInformation,
	locationdependent		MBS-ServiceAreaInformationList,
	choice-Extensions		ProtocolIE-SingleContainer { {MBSServiceArea-ExtIEs} }
}

MBSServiceArea-ExtIEs F1AP-PROTOCOL-IES ::= {
	...
}


MBS-ServiceAreaInformation ::= SEQUENCE {
	mBS-ServiceAreaCellList		MBS-ServiceAreaCellList																OPTIONAL,
	mBS-ServiceAreaTAIList		MBS-ServiceAreaTAIList																OPTIONAL,
	iE-Extensions					ProtocolExtensionContainer { {MBS-ServiceAreaInformation-ExtIEs} }	OPTIONAL,
	...
}

MBS-ServiceAreaInformation-ExtIEs F1AP-PROTOCOL-EXTENSION ::= {
	...
}

MBS-ServiceAreaCellList ::= SEQUENCE (SIZE(1.. maxnoofCellsforMBS)) OF NRCGI

MBS-ServiceAreaTAIList ::= SEQUENCE (SIZE(1.. maxnoofTAIforMBS)) OF MBS-ServiceAreaTAIList-Item
MBS-ServiceAreaTAIList-Item ::= SEQUENCE {
	plmn-ID							PLMN-Identity,
	five5-TAC						FiveGS-TAC,
	iE-Extensions					ProtocolExtensionContainer { {MBS-ServiceAreaTAIList-Item-ExtIEs} }	OPTIONAL,
	...
}

MBS-ServiceAreaTAIList-Item-ExtIEs F1AP-PROTOCOL-EXTENSION ::= {
	...
}


MBS-ServiceAreaInformationList ::= SEQUENCE (SIZE(1..maxnoofMBSServiceAreaInformation)) OF MBS-ServiceAreaInformationItem

MBS-ServiceAreaInformationItem ::= SEQUENCE {
	mBS-AreaSessionID					MBS-Area-Session-ID,
	mBS-ServiceAreaInformation 			MBS-ServiceAreaInformation,
	iE-Extensions						ProtocolExtensionContainer { { MBS-ServiceAreaInformationItem-ExtIEs} }	OPTIONAL,
	...
}
MBS-ServiceAreaInformationItem-ExtIEs F1AP-PROTOCOL-EXTENSION ::= {
	...
}

MC-PagingCell-Item ::= SEQUENCE {
	nRCGI			NRCGI,
	iE-Extensions	ProtocolExtensionContainer { { MC-PagingCell-ItemExtIEs } }	OPTIONAL
}

MC-PagingCell-ItemExtIEs 	F1AP-PROTOCOL-EXTENSION ::= {
	...
}


MIB-message ::= OCTET STRING

MeasConfig ::= OCTET STRING

MeasGapConfig ::= OCTET STRING

MeasGapSharingConfig ::= OCTET STRING

PosMeasurementAmount ::= ENUMERATED {ma0, ma1, ma2, ma4, ma8, ma16, ma32, ma64}

MeasurementBeamInfoRequest ::= ENUMERATED {true, ...}

MeasurementBeamInfo	 ::= SEQUENCE {
	pRS-Resource-ID				PRS-Resource-ID		OPTIONAL,
	pRS-Resource-Set-ID			PRS-Resource-Set-ID	OPTIONAL,
	sSB-Index					SSB-Index			OPTIONAL,
	iE-Extensions				ProtocolExtensionContainer { { MeasurementBeamInfo-ExtIEs} } OPTIONAL
}

MeasurementBeamInfo-ExtIEs F1AP-PROTOCOL-EXTENSION ::= {
	...
}


MeasurementTimingConfiguration ::= OCTET STRING

MessageIdentifier ::= BIT STRING (SIZE (16))


MeasurementTimeOccasion ::= ENUMERATED {o1, o4, ...}

MeasurementCharacteristicsRequestIndicator ::= BIT STRING (SIZE (16))

MRB-ProgressInformation ::= CHOICE {
	pdcp-SN12			INTEGER (0..4095),
	pdcp-SN18			INTEGER (0..262143),
	choice-extension		ProtocolIE-SingleContainer { { MRB-ProgressInformation-ExtIEs} }
}

MRB-ProgressInformation-ExtIEs F1AP-PROTOCOL-IES ::= {
	...
}

MulticastF1UContextReferenceF1 ::= OCTET STRING (SIZE(4))

MulticastF1UContextReferenceCU ::= OCTET STRING (SIZE(4))

MultipleULAoA ::= SEQUENCE {
	multipleULAoA					MultipleULAoA-List,
	iE-Extensions					ProtocolExtensionContainer { { MultipleULAoA-ExtIEs} } OPTIONAL,
	...
}

MultipleULAoA-ExtIEs F1AP-PROTOCOL-EXTENSION ::= {
	...
}

MultipleULAoA-List ::= SEQUENCE (SIZE(1.. maxnoofULAoAs)) OF MultipleULAoA-Item

MultipleULAoA-Item ::= CHOICE {
	uL-AoA		UL-AoA,
	ul-ZoA		ZoAInformation,
	choice-extension ProtocolIE-SingleContainer { { MultipleULAoA-Item-ExtIEs } }
}

MultipleULAoA-Item-ExtIEs F1AP-PROTOCOL-IES ::= {
	...
}

MDTPollutedMeasurementIndicator	::= ENUMERATED {iDC,no-IDC, ...}

MRB-ID ::= INTEGER (1..512, ...)

MulticastMBSSessionList ::= SEQUENCE (SIZE(1..maxnoofMBSSessionsofUE)) OF MulticastMBSSessionList-Item
MulticastMBSSessionList-Item ::= SEQUENCE {
	mbsSessionId				MBS-Session-ID,
	iE-Extensions				ProtocolExtensionContainer { { MulticastMBSSessionList-Item-ExtIEs } } OPTIONAL,
	...
}

MulticastMBSSessionList-Item-ExtIEs F1AP-PROTOCOL-EXTENSION ::= {
	...
}

MulticastMRBs-FailedToBeModified-Item ::= SEQUENCE {
	mRB-ID						MRB-ID,
	cause						Cause							OPTIONAL,
	iE-Extensions				ProtocolExtensionContainer { { MulticastMRBs-FailedtoBeModified-Item-ExtIEs} } OPTIONAL,
	...
}

MulticastMRBs-FailedtoBeModified-Item-ExtIEs F1AP-PROTOCOL-EXTENSION ::= {
	...
}

MulticastMRBs-FailedToBeSetup-Item ::= SEQUENCE {
	mRB-ID						MRB-ID,
	cause						Cause							OPTIONAL,
	iE-Extensions				ProtocolExtensionContainer { { MulticastMRBs-FailedToBeSetup-Item-ExtIEs} } OPTIONAL,
	...
}

MulticastMRBs-FailedToBeSetup-Item-ExtIEs F1AP-PROTOCOL-EXTENSION ::= {
	...
}

MulticastMRBs-FailedToBeSetupMod-Item ::= SEQUENCE {
	mRB-ID						MRB-ID,
	cause						Cause							OPTIONAL,
	iE-Extensions				ProtocolExtensionContainer { { MulticastMRBs-FailedToBeSetupMod-Item-ExtIEs} } OPTIONAL,
	...
}

MulticastMRBs-FailedToBeSetupMod-Item-ExtIEs F1AP-PROTOCOL-EXTENSION ::= {
	...
}

MulticastMRBs-Modified-Item ::= SEQUENCE {
	mRB-ID						MRB-ID,
	iE-Extensions				ProtocolExtensionContainer { { MulticastMRBs-Modified-Item-ExtIEs} } OPTIONAL,
	...
}

MulticastMRBs-Modified-Item-ExtIEs F1AP-PROTOCOL-EXTENSION ::= {
	...
}

MulticastMRBs-Setup-Item ::= SEQUENCE {
	mRB-ID						MRB-ID,
	iE-Extensions				ProtocolExtensionContainer { { MulticastMRBs-Setup-Item-ExtIEs} } OPTIONAL,
	...
}

MulticastMRBs-Setup-Item-ExtIEs F1AP-PROTOCOL-EXTENSION ::= {
	...
}

MulticastMRBs-SetupMod-Item ::= SEQUENCE {
	mRB-ID						MRB-ID,
	iE-Extensions				ProtocolExtensionContainer { { MulticastMRBs-SetupMod-Item-ExtIEs} } OPTIONAL,
	...
}

MulticastMRBs-SetupMod-Item-ExtIEs F1AP-PROTOCOL-EXTENSION ::= {
	...
}

MulticastMRBs-ToBeModified-Item ::= SEQUENCE {
	mRB-ID							MRB-ID,
	mRB-QoSInformation				QoSFlowLevelQoSParameters		OPTIONAL,
	mBS-Flows-Mapped-To-MRB-List	MBS-Flows-Mapped-To-MRB-List	OPTIONAL,
	mBS-DL-PDCP-SN-Length			PDCPSNLength 					OPTIONAL,
	iE-Extensions					ProtocolExtensionContainer { { MulticastMRBs-ToBeModified-Item-ExtIEs} } OPTIONAL,
	...
}

MulticastMRBs-ToBeModified-Item-ExtIEs F1AP-PROTOCOL-EXTENSION ::= {
	...
}

MulticastMRBs-ToBeReleased-Item	::= SEQUENCE {
	mRB-ID						MRB-ID,
	iE-Extensions				ProtocolExtensionContainer { { MulticastMRBs-ToBeReleased-ItemExtIEs } }	OPTIONAL,
	...
}

MulticastMRBs-ToBeReleased-ItemExtIEs 	F1AP-PROTOCOL-EXTENSION ::= {
	...
}

MulticastMRBs-ToBeSetup-Item ::= SEQUENCE {
	mRB-ID							MRB-ID,
	mRB-QoSInformation				QoSFlowLevelQoSParameters,
	mBS-Flows-Mapped-To-MRB-List	MBS-Flows-Mapped-To-MRB-List,
	mBS-DL-PDCP-SN-Length			PDCPSNLength,
	iE-Extensions					ProtocolExtensionContainer { { MulticastMRBs-ToBeSetup-Item-ExtIEs} },
	...
}

MulticastMRBs-ToBeSetup-Item-ExtIEs F1AP-PROTOCOL-EXTENSION ::= {
	...
}

MulticastMRBs-ToBeSetupMod-Item ::= SEQUENCE {
	mRB-ID							MRB-ID,
	mRB-QoSInformation				QoSFlowLevelQoSParameters,
	mBS-Flows-Mapped-To-MRB-List	MBS-Flows-Mapped-To-MRB-List,
	mBS-DL-PDCP-SN-Length			PDCPSNLength,
	iE-Extensions					ProtocolExtensionContainer { { MulticastMRBs-ToBeSetupMod-Item-ExtIEs} },
	...
}

MulticastMRBs-ToBeSetupMod-Item-ExtIEs F1AP-PROTOCOL-EXTENSION ::= {
	...
}

MultiplexingInfo 	::=	SEQUENCE{
	iAB-MT-Cell-List 	IAB-MT-Cell-List,
	iE-Extensions		ProtocolExtensionContainer { {MultiplexingInfo-ExtIEs} } OPTIONAL
}

MultiplexingInfo-ExtIEs 	F1AP-PROTOCOL-EXTENSION ::= {
	...
}

M2Configuration ::= ENUMERATED {true, ...}


M5Configuration ::= SEQUENCE {
	m5period			M5period,
	m5-links-to-log		M5-Links-to-log,
	iE-Extensions		ProtocolExtensionContainer { { M5Configuration-ExtIEs} } OPTIONAL,
	...
}

M5Configuration-ExtIEs F1AP-PROTOCOL-EXTENSION ::= {
	{ID	id-M5ReportAmount	CRITICALITY ignore	EXTENSION M5ReportAmount PRESENCE optional },
	...
}

M5period ::= ENUMERATED { ms1024, ms2048, ms5120, ms10240, min1, ... }

M5ReportAmount	::= ENUMERATED { r1, r2, r4, r8, r16, r32, r64, infinity, ... }

M5-Links-to-log	::= ENUMERATED {uplink, downlink, both-uplink-and-downlink, ...}


M6Configuration ::= SEQUENCE {
	m6report-Interval	M6report-Interval,
	m6-links-to-log		M6-Links-to-log,
	iE-Extensions		ProtocolExtensionContainer { { M6Configuration-ExtIEs} } OPTIONAL,
	...
}

M6Configuration-ExtIEs F1AP-PROTOCOL-EXTENSION ::= {
	{ID	id-M6ReportAmount	CRITICALITY ignore	EXTENSION M6ReportAmount PRESENCE optional },
	...
}

M6report-Interval ::= ENUMERATED { ms120, ms240, ms640, ms1024, ms2048, ms5120, ms10240, ms20480, ms40960, min1, min6, min12, min30, ..., ms480}

M6ReportAmount	::= ENUMERATED { r1, r2, r4, r8, r16, r32, r64, infinity, ... }


M6-Links-to-log	::= ENUMERATED {uplink, downlink, both-uplink-and-downlink, ...}


M7Configuration ::= SEQUENCE {
	m7period			M7period,
	m7-links-to-log		M7-Links-to-log,
	iE-Extensions		ProtocolExtensionContainer { { M7Configuration-ExtIEs} } OPTIONAL,
	...
}

M7Configuration-ExtIEs F1AP-PROTOCOL-EXTENSION ::= {
	{ID	id-M7ReportAmount	CRITICALITY ignore	EXTENSION M7ReportAmount PRESENCE optional},
	...
}

M7period	::= INTEGER(1..60, ...)

M7ReportAmount	::= ENUMERATED { r1, r2, r4, r8, r16, r32, r64, infinity, ... }

M7-Links-to-log	::= ENUMERATED {downlink, ...}

MDT-Activation ::= ENUMERATED {
	immediate-MDT-only,
	immediate-MDT-and-Trace,
	...
}

MDTConfiguration ::= SEQUENCE {
	mdt-Activation				MDT-Activation,
	measurementsToActivate		MeasurementsToActivate,
	m2Configuration				M2Configuration		OPTIONAL,
	--  C-ifM2: This IE shall be present if the Measurements to Activate IE has the second bit set to "1".
	m5Configuration				M5Configuration		OPTIONAL,
	--  C-ifM5: This IE shall be present if the Measurements to Activate IE has the fifth bit set to "1".
	m6Configuration				M6Configuration		OPTIONAL,
	--  C-ifM6: This IE shall be present if the Measurements to Activate IE has the seventh bit set to "1".
	m7Configuration				M7Configuration		OPTIONAL,
	--  C-ifM7: This IE shall be present if the Measurements to Activate IE has the eighth bit set to "1".
	iE-Extensions				ProtocolExtensionContainer { { MDTConfiguration-ExtIEs} } OPTIONAL,
	...
}
MDTConfiguration-ExtIEs F1AP-PROTOCOL-EXTENSION ::= {
	...
}


MDTPLMNList ::= SEQUENCE (SIZE(1..maxnoofMDTPLMNs)) OF PLMN-Identity

MDTPLMNModificationList ::= SEQUENCE (SIZE(0..maxnoofMDTPLMNs)) OF PLMN-Identity

MeasuredResultsValue ::= CHOICE {
	uL-AngleOfArrival	UL-AoA,
	uL-SRS-RSRP			UL-SRS-RSRP,
	uL-RTOA				UL-RTOA-Measurement,
	gNB-RxTxTimeDiff	GNB-RxTxTimeDiff,
	choice-extension	ProtocolIE-SingleContainer { { MeasuredResultsValue-ExtIEs } }
}

MeasuredResultsValue-ExtIEs F1AP-PROTOCOL-IES ::= {
	{ ID id-ZoAInformation	CRITICALITY reject TYPE ZoAInformation	PRESENCE mandatory}|
	{ ID id-MultipleULAoA	CRITICALITY reject TYPE MultipleULAoA	PRESENCE mandatory}|
	{ ID id-UL-SRS-RSRPP	CRITICALITY reject TYPE UL-SRS-RSRPP	PRESENCE mandatory},
	...
}

MeasurementsToActivate ::= BIT STRING (SIZE (8))

MUSIM-GapConfig ::= OCTET STRING


-- N

NA-Resource-Configuration-List ::= SEQUENCE (SIZE(1.. maxnoofHSNASlots)) OF NA-Resource-Configuration-Item

NA-Resource-Configuration-Item ::= SEQUENCE {
	nADownlink					NADownlink 	    OPTIONAL,
	nAUplink					NAUplink 	    OPTIONAL,
	nAFlexible					NAFlexible 	    OPTIONAL,
	iE-Extensions				ProtocolExtensionContainer { { NA-Resource-Configuration-Item-ExtIEs} } OPTIONAL
}

NA-Resource-Configuration-Item-ExtIEs 	F1AP-PROTOCOL-EXTENSION ::= {
	...
}

NADownlink ::= ENUMERATED { true, false, ...}
NAFlexible ::= ENUMERATED { true, false, ...}
NAUplink ::= ENUMERATED { true, false, ...}

Neighbour-Node-Cells-List ::= SEQUENCE (SIZE(1..maxnoofNeighbourNodeCellsIAB)) OF Neighbour-Node-Cells-List-Item

Neighbour-Node-Cells-List-Item ::= SEQUENCE{
	nRCGI			 								NRCGI,
	gNB-CU-UE-F1AP-ID	GNB-CU-UE-F1AP-ID 			OPTIONAL,
	gNB-DU-UE-F1AP-ID	GNB-DU-UE-F1AP-ID 			OPTIONAL,
	peer-Parent-Node-Indicator						ENUMERATED {true, ...} 	OPTIONAL,
	iAB-DU-Cell-Resource-Configuration-Mode-Info	IAB-DU-Cell-Resource-Configuration-Mode-Info 	OPTIONAL,
	iAB-STC-Info									IAB-STC-Info	OPTIONAL,
	rACH-Config-Common								RACH-Config-Common	OPTIONAL,
	rACH-Config-Common-IAB							RACH-Config-Common-IAB	OPTIONAL,
	cSI-RS-Configuration							OCTET STRING	OPTIONAL,
	sR-Configuration								OCTET STRING	OPTIONAL,
	pDCCH-ConfigSIB1								OCTET STRING	OPTIONAL,
	sCS-Common										OCTET STRING	OPTIONAL,
	iE-Extensions									ProtocolExtensionContainer {{Neighbour-Node-Cells-List-Item-ExtIEs}}		OPTIONAL
}

Neighbour-Node-Cells-List-Item-ExtIEs 	F1AP-PROTOCOL-EXTENSION ::= {
	...
}

NeedforGap::= ENUMERATED {true, ...}

NeedForGapsInfoNR ::= OCTET STRING

NeedForGapNCSGInfoNR ::= OCTET STRING

NeedForGapNCSGInfoEUTRA ::= OCTET STRING

Neighbour-Cell-Information-Item ::= SEQUENCE {
	nRCGI				NRCGI,
	intendedTDD-DL-ULConfig		IntendedTDD-DL-ULConfig OPTIONAL,
	iE-Extensions	ProtocolExtensionContainer { { Neighbour-Cell-Information-ItemExtIEs } }	OPTIONAL
}

Neighbour-Cell-Information-ItemExtIEs 	F1AP-PROTOCOL-EXTENSION ::= {
	...
}

NeighbourNR-CellsForSON-List ::= SEQUENCE (SIZE(1.. maxNeighbourCellforSON)) OF NeighbourNR-CellsForSON-Item

NeighbourNR-CellsForSON-Item ::= SEQUENCE {
	nRCGI											NRCGI,
	nR-ModeInfoRel16								NR-ModeInfoRel16												OPTIONAL,
	sSB-PositionsInBurst							SSB-PositionsInBurst											OPTIONAL,
	nRPRACHConfig									NRPRACHConfig													OPTIONAL,
	iE-Extensions						ProtocolExtensionContainer { { NeighbourNR-CellsForSON-Item-ExtIEs} }	OPTIONAL,
	...
}

NeighbourNR-CellsForSON-Item-ExtIEs 	F1AP-PROTOCOL-EXTENSION ::= {
	...
}

NGRANAllocationAndRetentionPriority ::= SEQUENCE {
	priorityLevel				PriorityLevel,
	pre-emptionCapability		Pre-emptionCapability,
	pre-emptionVulnerability	Pre-emptionVulnerability,
	iE-Extensions				ProtocolExtensionContainer { {NGRANAllocationAndRetentionPriority-ExtIEs} } OPTIONAL
}

NGRANAllocationAndRetentionPriority-ExtIEs F1AP-PROTOCOL-EXTENSION ::= {
	...
}


NGRANHighAccuracyAccessPointPosition ::= SEQUENCE {
	latitude					INTEGER (-2147483648.. 2147483647),
	longitude					INTEGER (-2147483648.. 2147483647),
	altitude					INTEGER (-64000..1280000),
	uncertaintySemi-major		INTEGER (0..255),
	uncertaintySemi-minor		INTEGER (0..255),
	orientationOfMajorAxis		INTEGER (0..179),
	horizontalConfidence		INTEGER (0..100),
	uncertaintyAltitude			INTEGER (0..255),
	verticalConfidence			INTEGER (0..100),

	iE-Extensions				ProtocolExtensionContainer { { NGRANHighAccuracyAccessPointPosition-ExtIEs} } OPTIONAL
}

NGRANHighAccuracyAccessPointPosition-ExtIEs F1AP-PROTOCOL-EXTENSION ::= {
	...
}

NID ::= BIT STRING (SIZE(44))

NonF1terminatingTopologyIndicator ::= ENUMERATED {
	true,
	...
}

NR-CGI-List-For-Restart-Item ::= SEQUENCE {
	nRCGI				NRCGI,
	iE-Extensions		ProtocolExtensionContainer { { NR-CGI-List-For-Restart-ItemExtIEs } }	OPTIONAL,
	...
}

NR-CGI-List-For-Restart-ItemExtIEs 	F1AP-PROTOCOL-EXTENSION ::= {
	...
}

NR-PRSBeamInformation ::= SEQUENCE {
	nR-PRSBeamInformationList		NR-PRSBeamInformationList,
	lCStoGCSTranslationList 		LCStoGCSTranslationList		OPTIONAL,
	iE-Extensions	ProtocolExtensionContainer { { NR-PRSBeamInformation-ExtIEs } } OPTIONAL
}

NR-PRSBeamInformation-ExtIEs F1AP-PROTOCOL-EXTENSION ::= {
	...
}

NR-PRSBeamInformationList ::= SEQUENCE (SIZE(1.. maxnoofPRS-ResourceSets)) OF NR-PRSBeamInformationItem

NR-PRSBeamInformationItem ::= SEQUENCE {
	pRSResourceSetID	PRS-Resource-Set-ID,
	pRSAngleList		PRSAngleList,
	iE-Extensions		ProtocolExtensionContainer { { NR-PRSBeamInformationItem-ExtIEs } } OPTIONAL
}

NR-PRSBeamInformationItem-ExtIEs F1AP-PROTOCOL-EXTENSION ::= {
	...
}

NR-TADV ::= INTEGER (0.. 7690)

NRRedCapUEIndication ::= ENUMERATED {true, ...}

NRPagingeDRXInformation ::= SEQUENCE {
	nrpaging-eDRX-Cycle-Idle		NRPaging-eDRX-Cycle-Idle,
	nrpaging-Time-Window			NRPaging-Time-Window												OPTIONAL,
	iE-Extensions					ProtocolExtensionContainer { {NRPagingeDRXInformation-ExtIEs} }	OPTIONAL,
	...
}

NRPagingeDRXInformation-ExtIEs F1AP-PROTOCOL-EXTENSION ::= {
	...
}

NRPaging-eDRX-Cycle-Idle ::= ENUMERATED {
	hfquarter, hfhalf, hf1, hf2, hf4,
	hf8, hf16, hf32, hf64, hf128, hf256, hf512, hf1024,
	...
}


NRPaging-Time-Window ::= ENUMERATED {
	s1, s2, s3, s4, s5,
	s6, s7, s8, s9, s10,
	s11, s12, s13, s14, s15, s16,
	...,
	s17, s18, s19, s20, s21,
	s22, s23, s24, s25, s26,
	s27, s28, s29, s30, s31, s32
}

NRPagingeDRXInformationforRRCINACTIVE ::= SEQUENCE {
	nrpaging-eDRX-Cycle-Inactive		NRPaging-eDRX-Cycle-Inactive,
	iE-Extensions			ProtocolExtensionContainer { { NRPagingeDRXInformationforRRCINACTIVE-ExtIEs} }	OPTIONAL,
	...
}

NRPagingeDRXInformationforRRCINACTIVE-ExtIEs F1AP-PROTOCOL-EXTENSION ::= {
	...
}

NRPaging-eDRX-Cycle-Inactive ::= ENUMERATED {
	hfquarter, hfhalf, hf1,
	...
}

NonDynamic5QIDescriptor	::= SEQUENCE {
	fiveQI						INTEGER (0..255, ...),
	qoSPriorityLevel			INTEGER (1..127)				OPTIONAL,
	averagingWindow 			AveragingWindow					OPTIONAL,
	maxDataBurstVolume			MaxDataBurstVolume				OPTIONAL,
	iE-Extensions	ProtocolExtensionContainer { { NonDynamic5QIDescriptor-ExtIEs } } OPTIONAL
}

NonDynamic5QIDescriptor-ExtIEs F1AP-PROTOCOL-EXTENSION ::= {
	{ ID id-CNPacketDelayBudgetDownlink	CRITICALITY ignore	EXTENSION ExtendedPacketDelayBudget		PRESENCE optional	}|
	{ ID id-CNPacketDelayBudgetUplink	CRITICALITY ignore	EXTENSION ExtendedPacketDelayBudget		PRESENCE optional	},
	...
}

NonDynamicPQIDescriptor	::= SEQUENCE {
	fiveQI						INTEGER (0..255, ...),
	qoSPriorityLevel			INTEGER (1..8, ...)				OPTIONAL,
	averagingWindow 			AveragingWindow					OPTIONAL,
	maxDataBurstVolume			MaxDataBurstVolume				OPTIONAL,
	iE-Extensions	ProtocolExtensionContainer { { NonDynamicPQIDescriptor-ExtIEs } } OPTIONAL
}

NonDynamicPQIDescriptor-ExtIEs F1AP-PROTOCOL-EXTENSION ::= {
	...
}

NonUPTrafficType ::=	ENUMERATED {ue-associated, non-ue-associated, non-f1, bap-control-pdu,...}

NoofDownlinkSymbols	::= INTEGER (0..14)

NoofUplinkSymbols	::= INTEGER (0..14)

Notification-Cause ::= ENUMERATED {fulfilled, not-fulfilled, ...}

NotificationControl ::= ENUMERATED {active, not-active, ...}

NotificationInformation ::= SEQUENCE {
	message-Identifier	MessageIdentifier,
	serialNumber		SerialNumber,
	iE-Extensions	ProtocolExtensionContainer { { NotificationInformationExtIEs} } OPTIONAL,
	...
}

NotificationInformationExtIEs		F1AP-PROTOCOL-EXTENSION ::= {
	...
}

NPNBroadcastInformation ::= CHOICE {
	sNPN-Broadcast-Information					NPN-Broadcast-Information-SNPN,
	pNI-NPN-Broadcast-Information				NPN-Broadcast-Information-PNI-NPN,
	choice-extension					ProtocolIE-SingleContainer { {NPNBroadcastInformation-ExtIEs} }
}

NPNBroadcastInformation-ExtIEs F1AP-PROTOCOL-IES ::= {
	...
}

NPN-Broadcast-Information-SNPN ::= SEQUENCE {
	broadcastSNPNID-List		BroadcastSNPN-ID-List,
	iE-Extension				ProtocolExtensionContainer { {NPN-Broadcast-Information-SNPN-ExtIEs} }	OPTIONAL,
	...
}

NPN-Broadcast-Information-SNPN-ExtIEs F1AP-PROTOCOL-EXTENSION ::= {
	...
}
NPN-Broadcast-Information-PNI-NPN ::= SEQUENCE {
	broadcastPNI-NPN-ID-Information		BroadcastPNI-NPN-ID-List,
	iE-Extension							ProtocolExtensionContainer { {NPN-Broadcast-Information-PNI-NPN-ExtIEs} }	OPTIONAL,
	...
}

NPN-Broadcast-Information-PNI-NPN-ExtIEs F1AP-PROTOCOL-EXTENSION ::= {
	...
}


NPNSupportInfo ::= CHOICE {
	sNPN-Information		NID,
	choice-extension		ProtocolIE-SingleContainer { { NPNSupportInfo-ExtIEs } }
}

NPNSupportInfo-ExtIEs		F1AP-PROTOCOL-IES ::= {
	...
}

NRCarrierList ::= SEQUENCE (SIZE(1..maxnoofNRSCSs)) OF NRCarrierItem

NRCarrierItem ::= SEQUENCE {
	carrierSCS						NRSCS,
	offsetToCarrier					INTEGER (0..2199, ...),
	carrierBandwidth				INTEGER (0..maxnoofPhysicalResourceBlocks, ...),
	iE-Extension					ProtocolExtensionContainer { {NRCarrierItem-ExtIEs} } 				OPTIONAL,
	...
}

NRCarrierItem-ExtIEs F1AP-PROTOCOL-EXTENSION ::= {
	...
}

NRFreqInfo ::=  SEQUENCE {
	nRARFCN			INTEGER (0..maxNRARFCN),
	sul-Information	SUL-Information		OPTIONAL,
	freqBandListNr	SEQUENCE (SIZE(1..maxnoofNrCellBands)) OF FreqBandNrItem,
	iE-Extensions	ProtocolExtensionContainer { { NRFreqInfoExtIEs} } OPTIONAL,
	...
}

NRFreqInfoExtIEs		F1AP-PROTOCOL-EXTENSION ::= {
	{ ID id-FrequencyShift7p5khz	CRITICALITY ignore	EXTENSION FrequencyShift7p5khz	PRESENCE optional },
	...
}

NRCGI ::= SEQUENCE {
	pLMN-Identity			PLMN-Identity,
	nRCellIdentity			NRCellIdentity,
	iE-Extensions			ProtocolExtensionContainer { {NRCGI-ExtIEs} } OPTIONAL,
	...
}

NRCGI-ExtIEs F1AP-PROTOCOL-EXTENSION ::= {
	...
}

NR-Mode-Info ::= CHOICE {
	fDD		FDD-Info,
	tDD		TDD-Info,
	choice-extension			ProtocolIE-SingleContainer { { NR-Mode-Info-ExtIEs} }
}

NR-Mode-Info-ExtIEs F1AP-PROTOCOL-IES ::= {
	{ ID id-NR-U		CRITICALITY ignore	TYPE NR-U-Channel-Info-List PRESENCE optional },
	...
}

NR-ModeInfoRel16 ::= CHOICE {
	fDD												FDD-InfoRel16,
	tDD												TDD-InfoRel16,
	choice-extension								ProtocolIE-SingleContainer { { NR-ModeInfoRel16-ExtIEs} }
}

NR-ModeInfoRel16-ExtIEs F1AP-PROTOCOL-IES ::= {
	...
}


NRPRACHConfig ::= SEQUENCE {
	ulPRACHConfigList			NRPRACHConfigList									OPTIONAL,
	sulPRACHConfigList			NRPRACHConfigList									OPTIONAL,
	iE-Extension				ProtocolExtensionContainer { {NRPRACHConfig-ExtIEs} } 	OPTIONAL,
	...
}

NRPRACHConfig-ExtIEs F1AP-PROTOCOL-EXTENSION ::= {
	...
}

NRCellIdentity ::= BIT STRING (SIZE(36))

NRNRB ::= ENUMERATED { nrb11, nrb18, nrb24, nrb25, nrb31, nrb32, nrb38, nrb51, nrb52, nrb65, nrb66, nrb78, nrb79, nrb93, nrb106, nrb107, nrb121, nrb132, nrb133, nrb135, nrb160, nrb162, nrb189, nrb216, nrb217, nrb245, nrb264, nrb270, nrb273, ..., nrb33, nrb62, nrb124, nrb148, nrb248, nrb44, nrb58, nrb92, nrb119, nrb188, nrb242}

NRPCI ::= INTEGER(0..1007)


NRPRACHConfigList ::= SEQUENCE (SIZE(0..maxnoofPRACHconfigs)) OF NRPRACHConfigItem

NRPRACHConfigItem ::= SEQUENCE {
	nRSCS					NRSCS,
	prachFreqStartfromCarrier	INTEGER (0..maxnoofPhysicalResourceBlocks-1, ...),
	prachFDM					ENUMERATED {one, two, four, eight, ...},
	prachConfigIndex			INTEGER (0..255, ..., 256..262),
	ssb-perRACH-Occasion		ENUMERATED {oneEighth, oneFourth, oneHalf, one,
											two, four, eight, sixteen, ...},
	freqDomainLength			FreqDomainLength,
	zeroCorrelZoneConfig		INTEGER (0..15),
	iE-Extension		ProtocolExtensionContainer { { NRPRACHConfigItem-ExtIEs} } 		OPTIONAL,
	...
}

NRPRACHConfigItem-ExtIEs F1AP-PROTOCOL-EXTENSION ::= {
	...
}

NRSCS ::= ENUMERATED { scs15, scs30, scs60, scs120, ..., scs480, scs960}

NRUERLFReportContainer ::= OCTET STRING


NR-U-Channel-Info-List ::= SEQUENCE (SIZE (1..maxnoofNR-UChannelIDs)) OF NR-U-Channel-Info-Item

NR-U-Channel-Info-Item ::= SEQUENCE {
	nr-U-channel-ID			INTEGER(1.. maxnoofNR-UChannelIDs,...),
	nR-ARFCN				INTEGER (0..maxNRARFCN),
	bandwidth				ENUMERATED{mHz-10,mHz-20,mHz-40, mHz-60, mHz-80,...},
	iE-Extensions			ProtocolExtensionContainer { { NR-U-Channel-Info-List-ExtIEs } }		OPTIONAL,
	...
}

NR-U-Channel-Info-List-ExtIEs	F1AP-PROTOCOL-EXTENSION ::= {
	...
}


NR-U-Channel-List ::= SEQUENCE (SIZE (1..maxnoofNR-UChannelIDs)) OF NR-U-Channel-Item

NR-U-Channel-Item ::= SEQUENCE {
	nR-U-ChannelID						INTEGER(1..maxnoofNR-UChannelIDs),
	channelOccupancyTimePercentageDL		ChannelOccupancyTimePercentage,
	energyDetectionThreshold				EnergyDetectionThreshold,
	iE-Extensions			ProtocolExtensionContainer { { NR-U-Channel-Item-ExtIEs} } OPTIONAL,
	...
}

NR-U-Channel-Item-ExtIEs F1AP-PROTOCOL-EXTENSION ::= {
	...
}


NumberofActiveUEs ::= INTEGER(0..16777215, ...)

NumberOfBroadcasts ::= INTEGER (0..65535)

NumberofBroadcastRequest ::= INTEGER (0..65535)


NumberOfTRPRxTEG ::= ENUMERATED {two, three, four, six, eight, ...}

NumberOfTRPRxTxTEG ::= ENUMERATED {wo, three, four, six, eight, ...}

NumDLULSymbols ::= SEQUENCE {
	numDLSymbols	INTEGER (0..13, ...),
	numULSymbols	INTEGER (0..13, ...),
	iE-Extensions			ProtocolExtensionContainer { { NumDLULSymbols-ExtIEs} } OPTIONAL
}

NumDLULSymbols-ExtIEs F1AP-PROTOCOL-EXTENSION ::= {
	{ ID id-permutation		CRITICALITY ignore	EXTENSION Permutation	    PRESENCE optional },
	...
}

NRV2XServicesAuthorized ::= SEQUENCE {
	vehicleUE			VehicleUE														OPTIONAL,
	pedestrianUE 		PedestrianUE													OPTIONAL,
	iE-Extensions		ProtocolExtensionContainer { {NRV2XServicesAuthorized-ExtIEs} }	OPTIONAL
}

NRV2XServicesAuthorized-ExtIEs F1AP-PROTOCOL-EXTENSION ::= {
	...
}

NRUESidelinkAggregateMaximumBitrate ::= SEQUENCE {
	uENRSidelinkAggregateMaximumBitrate		BitRate,
	iE-Extensions					ProtocolExtensionContainer { {NRUESidelinkAggregateMaximumBitrate-ExtIEs} } OPTIONAL
}

NRUESidelinkAggregateMaximumBitrate-ExtIEs F1AP-PROTOCOL-EXTENSION ::= {
	...
}

NZP-CSI-RS-ResourceID::= INTEGER  (0..191)


-- O

OffsetToPointA	::= INTEGER (0..2199,...)

OnDemandPRS-Info ::= SEQUENCE {
	onDemandPRSRequestAllowed				BIT STRING (SIZE (16)),
	allowedResourceSetPeriodicityValues		BIT STRING (SIZE (24))	OPTIONAL,
	allowedPRSBandwidthValues				BIT STRING (SIZE (64))	OPTIONAL,
	allowedResourceRepetitionFactorValues	BIT STRING (SIZE (8))	OPTIONAL,
	allowedResourceNumberOfSymbolsValues	BIT STRING (SIZE (8))	OPTIONAL,
	allowedCombSizeValues					BIT STRING (SIZE (8))	OPTIONAL,
	iE-Extensions	ProtocolExtensionContainer { { OnDemandPRS-Info-ExtIEs} } OPTIONAL,
	...
}

OnDemandPRS-Info-ExtIEs F1AP-PROTOCOL-EXTENSION ::= {
	...
}


-- P

PacketDelayBudget ::= INTEGER (0..1023, ...)

PacketErrorRate ::= SEQUENCE {
	pER-Scalar			PER-Scalar,
	pER-Exponent		PER-Exponent,
	iE-Extensions		ProtocolExtensionContainer { {PacketErrorRate-ExtIEs} }	OPTIONAL,
	...
}

PacketErrorRate-ExtIEs F1AP-PROTOCOL-EXTENSION ::= {
	...
}

PER-Scalar ::= INTEGER (0..9, ...)
PER-Exponent ::= INTEGER (0..9, ...)

PagingCell-Item ::= SEQUENCE {
	nRCGI		NRCGI	,
	iE-Extensions	ProtocolExtensionContainer { { PagingCell-ItemExtIEs } }	OPTIONAL
}

PagingCell-ItemExtIEs 	F1AP-PROTOCOL-EXTENSION ::= {
	{	ID id-LastUsedCellIndication					CRITICALITY ignore 	EXTENSION LastUsedCellIndication						PRESENCE optional }|
	{	ID id-PEISubgroupingSupportIndication			CRITICALITY ignore	EXTENSION PEISubgroupingSupportIndication			PRESENCE optional },
	...
}

PagingDRX ::= ENUMERATED {
	v32,
	v64,
	v128,
	v256,
	...
}

PagingIdentity ::=	CHOICE {
	rANUEPagingIdentity	RANUEPagingIdentity,
	cNUEPagingIdentity	CNUEPagingIdentity,
	choice-extension			ProtocolIE-SingleContainer { { PagingIdentity-ExtIEs } }
}

PagingCause ::= ENUMERATED { voice,	...}

PagingIdentity-ExtIEs F1AP-PROTOCOL-IES::= {
	...
}

PagingOrigin ::= ENUMERATED { non-3gpp,	...}

PagingPriority ::= ENUMERATED { priolevel1, priolevel2, priolevel3, priolevel4, priolevel5, priolevel6, priolevel7, priolevel8,...}

PEIPSAssistanceInfo ::= SEQUENCE {
	cNSubgroupID		CNSubgroupID,
	iE-Extensions	ProtocolExtensionContainer { { PEIPSAssistanceInfo-ExtIEs } }	OPTIONAL
}

PEIPSAssistanceInfo-ExtIEs 	F1AP-PROTOCOL-EXTENSION ::= {
	...
}

RelativePathDelay ::= CHOICE {
	k0					INTEGER (0..16351),
	k1					INTEGER (0..8176),
	k2					INTEGER (0..4088),
	k3					INTEGER (0..2044),
	k4					INTEGER (0..1022),
	k5					INTEGER (0..511),
	choice-extension			ProtocolIE-SingleContainer { { RelativePathDelay-ExtIEs } }
}

RelativePathDelay-ExtIEs F1AP-PROTOCOL-IES ::= {
	...
}

Parent-IAB-Nodes-NA-Resource-Configuration-List ::= SEQUENCE (SIZE(1..maxnoofHSNASlots)) OF Parent-IAB-Nodes-NA-Resource-Configuration-Item

Parent-IAB-Nodes-NA-Resource-Configuration-Item::= SEQUENCE {
	nADownlink					NADownlink 	    OPTIONAL,
	nAUplink					NAUplink 	    OPTIONAL,
	nAFlexible					NAFlexible 	    OPTIONAL,
	iE-Extensions		ProtocolExtensionContainer { { Parent-IAB-Nodes-NA-Resource-Configuration-Item-ExtIEs} } OPTIONAL
}

Parent-IAB-Nodes-NA-Resource-Configuration-Item-ExtIEs F1AP-PROTOCOL-EXTENSION ::= {
	...
}

PartialSuccessCell ::= SEQUENCE {
	broadcastCellList		BroadcastCellList,
	iE-Extensions				ProtocolExtensionContainer { { PartialSuccessCell-ExtIEs} } OPTIONAL,
	...
}
PartialSuccessCell-ExtIEs F1AP-PROTOCOL-EXTENSION ::= {
	...
}

PathlossReferenceInfo ::= SEQUENCE {
	pathlossReferenceSignal			PathlossReferenceSignal,
	iE-Extensions					ProtocolExtensionContainer { {PathlossReferenceInfo-ExtIEs} }	OPTIONAL
}

PathlossReferenceInfo-ExtIEs F1AP-PROTOCOL-EXTENSION ::= {
	...
}

PathlossReferenceSignal ::= CHOICE {
	sSB										SSB,
	dL-PRS									DL-PRS,
	choice-extension						ProtocolIE-SingleContainer {{PathlossReferenceSignal-ExtIEs }}
}

PathlossReferenceSignal-ExtIEs F1AP-PROTOCOL-IES ::= {
	...
}

PathSwitchConfiguration ::= SEQUENCE {
	targetRelayUEID			BIT STRING(SIZE(24)),
	remoteUELocalID			RemoteUELocalID,
	t420					ENUMERATED {ms50, ms100, ms150, ms200, ms500, ms1000, ms2000, ms10000},
	iE-Extensions			ProtocolExtensionContainer { { PathSwitchConfiguration-ExtIEs } }		OPTIONAL,
	...
}

PathSwitchConfiguration-ExtIEs	F1AP-PROTOCOL-EXTENSION ::= {
	...
}

PC5QoSFlowIdentifier ::= INTEGER (1..2048)

PC5-QoS-Characteristics ::= CHOICE {
	non-Dynamic-PQI				NonDynamicPQIDescriptor,
	dynamic-PQI					DynamicPQIDescriptor,
	choice-extension			ProtocolIE-SingleContainer { { PC5-QoS-Characteristics-ExtIEs } }
}

PC5-QoS-Characteristics-ExtIEs F1AP-PROTOCOL-IES ::= {
	...
}


PC5QoSParameters	::= SEQUENCE {
    pC5-QoS-Characteristics				PC5-QoS-Characteristics,
	pC5-QoS-Flow-Bit-Rates				PC5FlowBitRates				OPTIONAL,
	iE-Extensions						ProtocolExtensionContainer { { PC5QoSParameters-ExtIEs } }	OPTIONAL,
	...
}

PC5QoSParameters-ExtIEs	F1AP-PROTOCOL-EXTENSION ::= {
	...
}

PC5FlowBitRates ::= SEQUENCE {
	guaranteedFlowBitRate		BitRate,
	maximumFlowBitRate			BitRate,
	iE-Extensions				ProtocolExtensionContainer { { PC5FlowBitRates-ExtIEs } }	OPTIONAL,
	...
}

PC5FlowBitRates-ExtIEs	F1AP-PROTOCOL-EXTENSION ::= {
	...
}

PC5RLCChannelID ::= INTEGER (1..512, ...)

PC5RLCChannelQoSInformation ::= CHOICE {
	pC5RLCChannelQoS				QoSFlowLevelQoSParameters,
	pC5ControlPlaneTrafficType		ENUMERATED {srb1,srb2,...},
	choice-extension				ProtocolIE-SingleContainer { { PC5RLCChannelQoSInformation-ExtIEs} }
}

PC5RLCChannelQoSInformation-ExtIEs F1AP-PROTOCOL-IES ::= {
	...
}

PC5RLCChannelToBeSetupList ::= SEQUENCE (SIZE(1.. maxnoofPC5RLCChannels)) OF PC5RLCChannelToBeSetupItem

PC5RLCChannelToBeSetupItem ::= SEQUENCE {
	pC5RLCChannelID					PC5RLCChannelID,
	remoteUELocalID					RemoteUELocalID			OPTIONAL,
	pC5RLCChannelQoSInformation		PC5RLCChannelQoSInformation,
	rLCMode							RLCMode,
	iE-Extensions					ProtocolExtensionContainer { { PC5RLCChannelToBeSetupItem-ExtIEs } }	OPTIONAL,
	...
}

PC5RLCChannelToBeSetupItem-ExtIEs	F1AP-PROTOCOL-EXTENSION ::= {
	...
}

PC5RLCChannelToBeModifiedList ::= SEQUENCE (SIZE(1.. maxnoofPC5RLCChannels)) OF PC5RLCChannelToBeModifiedItem

PC5RLCChannelToBeModifiedItem ::= SEQUENCE {
	pC5RLCChannelID					PC5RLCChannelID,
	remoteUELocalID					RemoteUELocalID			OPTIONAL,
	pC5RLCChannelQoSInformation		PC5RLCChannelQoSInformation			OPTIONAL,
	rLCMode							RLCMode			OPTIONAL,
	iE-Extensions					ProtocolExtensionContainer { { PC5RLCChannelToBeModifiedItem-ExtIEs } }	OPTIONAL,
	...
}

PC5RLCChannelToBeModifiedItem-ExtIEs	F1AP-PROTOCOL-EXTENSION ::= {
	...
}

PC5RLCChannelToBeReleasedList ::= SEQUENCE (SIZE(1.. maxnoofPC5RLCChannels)) OF PC5RLCChannelToBeReleasedItem

PC5RLCChannelToBeReleasedItem ::= SEQUENCE {
	pC5RLCChannelID					PC5RLCChannelID,
	remoteUELocalID					RemoteUELocalID			OPTIONAL,
	iE-Extensions					ProtocolExtensionContainer { { PC5RLCChannelToBeReleasedItem-ExtIEs } }	OPTIONAL,
	...
}

PC5RLCChannelToBeReleasedItem-ExtIEs	F1AP-PROTOCOL-EXTENSION ::= {
	...
}

PC5RLCChannelSetupList ::= SEQUENCE (SIZE(1.. maxnoofPC5RLCChannels)) OF PC5RLCChannelSetupItem

PC5RLCChannelSetupItem ::= SEQUENCE {
	pC5RLCChannelID					PC5RLCChannelID,
	remoteUELocalID					RemoteUELocalID			OPTIONAL,
	iE-Extensions					ProtocolExtensionContainer { { PC5RLCChannelSetupItem-ExtIEs } }	OPTIONAL,
	...
}

PC5RLCChannelSetupItem-ExtIEs	F1AP-PROTOCOL-EXTENSION ::= {
	...
}

PC5RLCChannelFailedToBeSetupList ::= SEQUENCE (SIZE(1.. maxnoofPC5RLCChannels)) OF PC5RLCChannelFailedToBeSetupItem

PC5RLCChannelFailedToBeSetupItem ::= SEQUENCE {
	pC5RLCChannelID					PC5RLCChannelID,
	remoteUELocalID					RemoteUELocalID			OPTIONAL,
	cause							Cause					OPTIONAL,
	iE-Extensions					ProtocolExtensionContainer { { PC5RLCChannelFailedToBeSetupItem-ExtIEs } }	OPTIONAL,
	...
}

PC5RLCChannelFailedToBeSetupItem-ExtIEs	F1AP-PROTOCOL-EXTENSION ::= {
	...
}

PC5RLCChannelModifiedList ::= SEQUENCE (SIZE(1.. maxnoofPC5RLCChannels)) OF PC5RLCChannelModifiedItem

PC5RLCChannelModifiedItem ::= SEQUENCE {
	pC5RLCChannelID					PC5RLCChannelID,
	remoteUELocalID					RemoteUELocalID			OPTIONAL,
	iE-Extensions					ProtocolExtensionContainer { { PC5RLCChannelModifiedItem-ExtIEs } }	OPTIONAL,
	...
}

PC5RLCChannelModifiedItem-ExtIEs	F1AP-PROTOCOL-EXTENSION ::= {
	...
}

PC5RLCChannelFailedToBeModifiedList ::= SEQUENCE (SIZE(1.. maxnoofPC5RLCChannels)) OF PC5RLCChannelFailedToBeModifiedItem

PC5RLCChannelFailedToBeModifiedItem ::= SEQUENCE {
	pC5RLCChannelID					PC5RLCChannelID,
	remoteUELocalID					RemoteUELocalID			OPTIONAL,
	cause							Cause	OPTIONAL,
	iE-Extensions					ProtocolExtensionContainer { { PC5RLCChannelFailedToBeModifiedItem-ExtIEs } }	OPTIONAL,
	...
}

PC5RLCChannelFailedToBeModifiedItem-ExtIEs	F1AP-PROTOCOL-EXTENSION ::= {
	...
}

PC5RLCChannelRequiredToBeModifiedList ::= SEQUENCE (SIZE(1.. maxnoofPC5RLCChannels)) OF PC5RLCChannelRequiredToBeModifiedItem

PC5RLCChannelRequiredToBeModifiedItem ::= SEQUENCE {
	pC5RLCChannelID					PC5RLCChannelID,
	remoteUELocalID					RemoteUELocalID			OPTIONAL,
	iE-Extensions					ProtocolExtensionContainer { { PC5RLCChannelRequiredToBeModifiedItem-ExtIEs } }	OPTIONAL,
	...
}

PC5RLCChannelRequiredToBeModifiedItem-ExtIEs	F1AP-PROTOCOL-EXTENSION ::= {
	...
}

PC5RLCChannelRequiredToBeReleasedList ::= SEQUENCE (SIZE(1.. maxnoofPC5RLCChannels)) OF PC5RLCChannelRequiredToBeReleasedItem

PC5RLCChannelRequiredToBeReleasedItem ::= SEQUENCE {
	pC5RLCChannelID					PC5RLCChannelID,
	remoteUELocalID					RemoteUELocalID			OPTIONAL,
	iE-Extensions					ProtocolExtensionContainer { { PC5RLCChannelRequiredToBeReleasedItem-ExtIEs } }	OPTIONAL,
	...
}

PC5RLCChannelRequiredToBeReleasedItem-ExtIEs	F1AP-PROTOCOL-EXTENSION ::= {
	...
}

PDCCH-BlindDetectionSCG ::= OCTET STRING

PDCMeasurementPeriodicity ::= ENUMERATED
{ms80, ms120, ms160, ms240, ms320, ms480, ms640, ms1024, ms1280, ms2048, ms2560, ms5120, ...}

PDCMeasurementQuantities ::= SEQUENCE (SIZE (1.. maxnoofMeasPDC)) OF ProtocolIE-SingleContainer { {PDCMeasurementQuantities-ItemIEs} }

PDCMeasurementQuantities-ItemIEs F1AP-PROTOCOL-IES ::= {
	{ ID id-PDCMeasurementQuantities-Item	CRITICALITY reject	TYPE PDCMeasurementQuantities-Item		PRESENCE mandatory}
}

PDCMeasurementQuantities-Item ::= SEQUENCE {
	pDCmeasurementQuantitiesValue				PDCMeasurementQuantitiesValue,
	iE-Extensions								ProtocolExtensionContainer { { PDCMeasurementQuantitiesValue-ExtIEs} } OPTIONAL
}

PDCMeasurementQuantitiesValue-ExtIEs F1AP-PROTOCOL-EXTENSION ::= {
	...
}

PDCMeasurementQuantitiesValue ::= ENUMERATED {
	nr-pdc-tadv,
	gNB-rx-tx,
	...
}

PDCMeasurementResult ::= SEQUENCE {
	pDCMeasuredResultsList			PDCMeasuredResultsList,
	iE-Extensions					ProtocolExtensionContainer { { PDCMeasurementResult-ExtIEs} } OPTIONAL
}

PDCMeasurementResult-ExtIEs F1AP-PROTOCOL-EXTENSION ::= {
	...
}

PDCMeasuredResultsList ::= SEQUENCE (SIZE(1..maxnoofMeasPDC)) OF PDCMeasuredResults-Item

PDCMeasuredResults-Item ::= SEQUENCE {
	pDCMeasuredResults-Value	PDCMeasuredResults-Value,
	iE-Extensions				ProtocolExtensionContainer {{ PDCMeasuredResults-Item-ExtIEs }}	 OPTIONAL
}

PDCMeasuredResults-Item-ExtIEs F1AP-PROTOCOL-EXTENSION ::= {
	...
}

PDCMeasuredResults-Value ::= CHOICE {
	pDC-TADV-NR				PDC-TADV-NR,
	pDC-RxTxTimeDiff		PDC-RxTxTimeDiff,
	choice-extension		ProtocolIE-SingleContainer { { PDCMeasuredResults-Value-ExtIEs} }
}

PDCMeasuredResults-Value-ExtIEs F1AP-PROTOCOL-IES ::= {
	...
}

PDCReportType ::= ENUMERATED {
	onDemand,
	periodic,
	...
}

PDC-RxTxTimeDiff ::= INTEGER (0..61565, ...)

PDC-TADV-NR ::= INTEGER (0..62500, ...)

PDCP-SN ::= INTEGER (0..4095)

PDCPSNLength	::= ENUMERATED { twelve-bits,eighteen-bits,...}

PDUSessionID ::= INTEGER (0..255)

PEISubgroupingSupportIndication ::= ENUMERATED {true, ...}

ReportingPeriodicityValue ::= INTEGER (0..512, ...)

Periodicity ::= INTEGER (0..640000, ...)

PeriodicitySRS ::= ENUMERATED { ms0p125, ms0p25, ms0p5, ms0p625, ms1, ms1p25, ms2, ms2p5, ms4, ms5, ms8, ms10, ms16, ms20, ms32, ms40, ms64, ms80, ms160, ms320, ms640, ms1280, ms2560, ms5120, ms10240, ...}

PeriodicityList ::= SEQUENCE (SIZE(1.. maxnoSRS-ResourcePerSet)) OF PeriodicityList-Item

PeriodicityList-Item ::= SEQUENCE {
	periodicitySRS				PeriodicitySRS,
	iE-Extensions				ProtocolExtensionContainer { { PeriodicityList-ItemExtIEs} } OPTIONAL
}

PeriodicityList-ItemExtIEs 	F1AP-PROTOCOL-EXTENSION ::= {
	...
}


Permutation ::= ENUMERATED {dfu, ufd, ...}

Ph-InfoMCG  ::= OCTET STRING

Ph-InfoSCG  ::= OCTET STRING

PLMN-Identity ::= OCTET STRING (SIZE(3))

PlayoutDelayForMediaStartup ::= OCTET STRING

PortNumber ::= BIT STRING (SIZE (16))


PosAssistance-Information ::= OCTET STRING

PosAssistanceInformationFailureList ::= OCTET STRING

PosBroadcast ::= ENUMERATED {
	start,
	stop,
	...
}

PosConextRevIndication ::= ENUMERATED {true, ...}

PositioningBroadcastCells ::= SEQUENCE (SIZE (1..maxnoBcastCell)) OF NRCGI


PosMeasGapPreConfigList ::= SEQUENCE {
	posMeasGapPreConfigToAddModList				OCTET STRING					OPTIONAL,
	posMeasGapPreConfigToReleaseList			OCTET STRING					OPTIONAL,
	iE-Extensions	ProtocolExtensionContainer { { PosMeasGapPreConfigList-ExtIEs} } OPTIONAL
}

PosMeasGapPreConfigList-ExtIEs F1AP-PROTOCOL-EXTENSION ::= {
	...
}

MeasurementPeriodicity ::= ENUMERATED
{ms120, ms240, ms480, ms640, ms1024, ms2048, ms5120, ms10240, min1, min6, min12, min30, ..., ms20480, ms40960, extended }


MeasurementPeriodicityExtended ::= ENUMERATED {ms160, ms320, ms1280, ms2560, ms61440, ms81920,	ms368640, ms737280, ms1843200,	...}

PosMeasurementPeriodicityNR-AoA ::= ENUMERATED {
	ms160,
	ms320,
	ms640,
	ms1280,
	ms2560,
	ms5120,
	ms10240,
	ms20480,
	ms40960,
	ms61440,
	ms81920,
	ms368640,
	ms737280,
	ms1843200,
	...

}

PosMeasurementQuantities ::= SEQUENCE (SIZE(1.. maxnoofPosMeas)) OF PosMeasurementQuantities-Item

PosMeasurementQuantities-Item ::= SEQUENCE {
	posMeasurementType					PosMeasurementType,
	timingReportingGranularityFactor	INTEGER (0..5) OPTIONAL,
	iE-Extensions						ProtocolExtensionContainer { { PosMeasurementQuantities-ItemExtIEs} } OPTIONAL
}

PosMeasurementQuantities-ItemExtIEs 	F1AP-PROTOCOL-EXTENSION ::= {
	...
}

PosMeasurementResult ::= SEQUENCE (SIZE (1.. maxnoofPosMeas)) OF PosMeasurementResultItem

PosMeasurementResultItem ::= SEQUENCE {
	measuredResultsValue				MeasuredResultsValue,
	timeStamp							TimeStamp,
	measurementQuality					TRPMeasurementQuality	OPTIONAL,
	measurementBeamInfo					MeasurementBeamInfo		OPTIONAL,
	iE-Extensions	ProtocolExtensionContainer { { PosMeasurementResultItemExtIEs } }	OPTIONAL
}

PosMeasurementResultItemExtIEs 	F1AP-PROTOCOL-EXTENSION ::= {
	{ ID id-ARP-ID				CRITICALITY ignore EXTENSION ARP-ID 					PRESENCE optional}|
	{ ID id-SRSResourcetype		CRITICALITY ignore EXTENSION SRSResourcetype 			PRESENCE optional}|
	{ ID id-LoS-NLoSInformation	CRITICALITY ignore EXTENSION LoS-NLoSInformation		PRESENCE optional },
	...
}

PosMeasurementResultList ::= SEQUENCE (SIZE(1.. maxNoOfMeasTRPs)) OF PosMeasurementResultList-Item

PosMeasurementResultList-Item ::= SEQUENCE {
	posMeasurementResult			PosMeasurementResult,
	tRPID							TRPID,
	iE-Extensions					ProtocolExtensionContainer { { PosMeasurementResultList-ItemExtIEs} } OPTIONAL
}

PosMeasurementResultList-ItemExtIEs 	F1AP-PROTOCOL-EXTENSION ::= {
	{ ID id-NRCGI	CRITICALITY ignore EXTENSION NRCGI		PRESENCE optional },
	...
}

PosMeasurementType ::= ENUMERATED {
	gnb-rx-tx,
	ul-srs-rsrp,
	ul-aoa,
	ul-rtoa,
	... ,
	multiple-ul-aoa,
	ul-srs-rsrpp
}

PosReportCharacteristics ::= ENUMERATED {
	ondemand,
	periodic,
	...
}

PosResourceSetType  ::= CHOICE {
	periodic			PosResourceSetTypePR,
	semi-persistent		PosResourceSetTypeSP,
	aperiodic			PosResourceSetTypeAP,
	choice-extension	ProtocolIE-SingleContainer {{ PosResourceSetType-ExtIEs }}
}

PosResourceSetType-ExtIEs F1AP-PROTOCOL-IES ::= {
	...
}

PosResourceSetTypePR ::= SEQUENCE {
	posperiodicSet		ENUMERATED{true, ...},
	iE-Extensions		ProtocolExtensionContainer { { PosResourceSetTypePR-ExtIEs} }	OPTIONAL
}

PosResourceSetTypePR-ExtIEs F1AP-PROTOCOL-EXTENSION ::= {
	...
}

PosResourceSetTypeSP ::= SEQUENCE {
	possemi-persistentSet		ENUMERATED{true, ...},
	iE-Extensions				ProtocolExtensionContainer { { PosResourceSetTypeSP-ExtIEs} }	OPTIONAL
}

PosResourceSetTypeSP-ExtIEs F1AP-PROTOCOL-EXTENSION ::= {
	...
}

PosResourceSetTypeAP ::= SEQUENCE {
	sRSResourceTrigger-List		INTEGER(1..3),
	iE-Extensions				ProtocolExtensionContainer { { PosResourceSetTypeAP-ExtIEs} }	OPTIONAL
}

PosResourceSetTypeAP-ExtIEs F1AP-PROTOCOL-EXTENSION ::= {
	...
}

PosSItypeList ::= SEQUENCE (SIZE(1.. maxnoofPosSITypes)) OF PosSItype-Item
PosSItype-Item ::= SEQUENCE {
	posItype			PosSItype   ,
	iE-Extensions	ProtocolExtensionContainer { { PosSItype-ItemExtIEs } } OPTIONAL
}

PosSItype-ItemExtIEs    F1AP-PROTOCOL-EXTENSION ::= {
	...
}

PosSItype ::= INTEGER (1..32, ...)

PosSRSResourceID-List ::= SEQUENCE (SIZE (1..maxnoSRS-PosResourcePerSet)) OF SRSPosResourceID

PosSRSResource-Item ::= SEQUENCE {
	srs-PosResourceId				SRSPosResourceID,
	transmissionCombPos				TransmissionCombPos,
	startPosition					INTEGER (0..13),
	nrofSymbols						ENUMERATED {n1, n2, n4, n8, n12},
	freqDomainShift					INTEGER (0..268),
	c-SRS							INTEGER (0..63),
	groupOrSequenceHopping			ENUMERATED { neither, groupHopping, sequenceHopping },
	resourceTypePos					ResourceTypePos,
	sequenceId						INTEGER (0.. 65535),
	spatialRelationPos				SpatialRelationPos 	OPTIONAL,
	iE-Extensions					ProtocolExtensionContainer { { PosSRSResource-Item-ExtIEs} }	OPTIONAL
}

PosSRSResource-Item-ExtIEs F1AP-PROTOCOL-EXTENSION ::= {
	...
}

PosSRSResource-List ::= SEQUENCE (SIZE (1..maxnoSRS-PosResources)) OF PosSRSResource-Item

PosSRSResourceSet-Item ::= SEQUENCE {
	possrsResourceSetID				INTEGER(0..15),
	possRSResourceID-List			PosSRSResourceID-List,
	posresourceSetType				PosResourceSetType,
	iE-Extensions		ProtocolExtensionContainer { { PosSRSResourceSet-Item-ExtIEs} }	OPTIONAL
}

PosSRSResourceSet-Item-ExtIEs F1AP-PROTOCOL-EXTENSION ::= {
	...
}

PosSRSResourceSet-List ::= SEQUENCE (SIZE (1..maxnoSRS-PosResourceSets)) OF PosSRSResourceSet-Item

PrimaryPathIndication ::= ENUMERATED {
	true,
	false,
	...
}

Pre-emptionCapability ::= ENUMERATED {
	shall-not-trigger-pre-emption,
	may-trigger-pre-emption
}

Pre-emptionVulnerability ::= ENUMERATED {
	not-pre-emptable,
	pre-emptable
}

PriorityLevel	::= INTEGER { spare (0), highest (1), lowest (14), no-priority (15) } (0..15)

ProtectedEUTRAResourceIndication		::= OCTET STRING

Protected-EUTRA-Resources-Item ::= SEQUENCE {
	spectrumSharingGroupID					SpectrumSharingGroupID,
	eUTRACells-List		EUTRACells-List,
	iE-Extensions		ProtocolExtensionContainer { { Protected-EUTRA-Resources-ItemExtIEs } }	OPTIONAL
}

Protected-EUTRA-Resources-ItemExtIEs 	F1AP-PROTOCOL-EXTENSION ::= {
	...
}

PRSConfiguration ::= SEQUENCE {
	pRSResourceSet-List			PRSResourceSet-List,
	iE-Extensions				ProtocolExtensionContainer { { PRSConfiguration-ExtIEs } }	OPTIONAL
}

PRSConfiguration-ExtIEs 	F1AP-PROTOCOL-EXTENSION ::= {
	...
}

PRSInformationPos  ::= SEQUENCE {
	pRS-IDPos					INTEGER(0..255),
	pRS-Resource-Set-IDPos		INTEGER(0..7),
	pRS-Resource-IDPos			INTEGER(0..63)	OPTIONAL,
	iE-Extensions				ProtocolExtensionContainer { { PRSInformationPos-ExtIEs} } OPTIONAL
}

PRSInformationPos-ExtIEs F1AP-PROTOCOL-EXTENSION ::= {
	...
}

PRS-Measurement-Info-List ::= SEQUENCE (SIZE(1..maxFreqLayers)) OF PRS-Measurement-Info-List-Item

PRS-Measurement-Info-List-Item ::= SEQUENCE {
	pointA						INTEGER (0..3279165),
	measPRSPeriodicity			ENUMERATED {ms20, ms40, ms80, ms160, ...},
	measPRSOffset				INTEGER (0..159, ...),
	measurementPRSLength		ENUMERATED {ms1dot5, ms3, ms3dot5, ms4, ms5dot5, ms6, ms10, ms20},
	iE-Extensions				ProtocolExtensionContainer { { PRS-Measurement-Info-List-Item-ExtIEs} } OPTIONAL,
		...
}

PRS-Measurement-Info-List-Item-ExtIEs F1AP-PROTOCOL-EXTENSION ::= {
	...
}


Potential-SpCell-Item ::= SEQUENCE {
	potential-SpCell-ID			NRCGI	,
	iE-Extensions				ProtocolExtensionContainer { { Potential-SpCell-ItemExtIEs } }	OPTIONAL,
	...
}

Potential-SpCell-ItemExtIEs 	F1AP-PROTOCOL-EXTENSION ::= {
	...
}


PRSAngleList ::= SEQUENCE (SIZE(1.. maxnoofPRS-ResourcesPerSet)) OF PRSAngleItem

PRSAngleItem ::= SEQUENCE {
	nR-PRS-Azimuth			INTEGER (0..359),
	nR-PRS-Azimuth-fine		INTEGER (0..9),
	nR-PRS-Elevation		INTEGER (0..180),
	nR-PRS-Elevation-fine	INTEGER (0..9),
	iE-Extensions			ProtocolExtensionContainer { { PRSAngleItem-ItemExtIEs } }	OPTIONAL
}

PRSAngleItem-ItemExtIEs 	F1AP-PROTOCOL-EXTENSION ::= {
	{ ID id-PRS-Resource-ID		CRITICALITY ignore EXTENSION PRS-Resource-ID		PRESENCE optional },
	...
}

PRSConfigRequestType ::= ENUMERATED {configure, off, ...}

PRSMuting::= SEQUENCE {
	pRSMutingOption1			PRSMutingOption1		OPTIONAL,
	pRSMutingOption2			PRSMutingOption2		OPTIONAL,
	iE-Extensions				ProtocolExtensionContainer { { PRSMuting-ExtIEs} } OPTIONAL
}

PRSMuting-ExtIEs F1AP-PROTOCOL-EXTENSION ::= {
	...
}

PRSMutingOption1 ::= SEQUENCE {
	mutingPattern					DL-PRSMutingPattern,
	mutingBitRepetitionFactor		ENUMERATED{rf1,rf2,rf4,rf8,...},
	iE-Extensions					ProtocolExtensionContainer { { PRSMutingOption1-ExtIEs} } OPTIONAL
}

PRSMutingOption1-ExtIEs F1AP-PROTOCOL-EXTENSION ::= {
	...
}

PRSMutingOption2 ::= SEQUENCE {
	mutingPattern					DL-PRSMutingPattern,
	iE-Extensions					ProtocolExtensionContainer { { PRSMutingOption2-ExtIEs} } OPTIONAL
}

PRSMutingOption2-ExtIEs F1AP-PROTOCOL-EXTENSION ::= {
	...
}

PRS-Resource-ID ::= INTEGER (0..63)

PRSResource-List::= SEQUENCE (SIZE (1..maxnoofPRSresources)) OF PRSResource-Item

PRSResource-Item  ::= SEQUENCE {
	pRSResourceID			PRS-Resource-ID,
	sequenceID				INTEGER(0..4095),
	rEOffset				INTEGER(0..11,...),
	resourceSlotOffset		INTEGER(0..511),
	resourceSymbolOffset	INTEGER(0..12),
	qCLInfo					PRSResource-QCLInfo		OPTIONAL,
	iE-Extensions			ProtocolExtensionContainer { { PRSResource-Item-ExtIEs} } OPTIONAL
}

PRSResource-Item-ExtIEs F1AP-PROTOCOL-EXTENSION ::= {
	...
}

PRSResource-QCLInfo  ::= CHOICE {
	qCLSourceSSB		PRSResource-QCLSourceSSB,
	qCLSourcePRS		PRSResource-QCLSourcePRS,
	choice-extension	ProtocolIE-SingleContainer { { PRSResource-QCLInfo-ExtIEs } }
}
PRSResource-QCLInfo-ExtIEs F1AP-PROTOCOL-IES ::= {
	...
}

PRSResource-QCLSourceSSB ::= SEQUENCE {
	pCI-NR				INTEGER(0..1007),
	sSB-Index 			SSB-Index OPTIONAL,
	iE-Extensions		ProtocolExtensionContainer { { PRSResource-QCLSourceSSB-ExtIEs} } OPTIONAL,
	...
}

PRSResource-QCLSourceSSB-ExtIEs F1AP-PROTOCOL-EXTENSION ::= {
	...
}

PRSResource-QCLSourcePRS ::= SEQUENCE {
	qCLSourcePRSResourceSetID		PRS-Resource-Set-ID,
	qCLSourcePRSResourceID 			PRS-Resource-ID OPTIONAL,
	iE-Extensions					ProtocolExtensionContainer { { PRSResource-QCLSourcePRS-ExtIEs} } OPTIONAL
}

PRSResource-QCLSourcePRS-ExtIEs F1AP-PROTOCOL-EXTENSION ::= {
	...
}

PRS-Resource-Set-ID ::= INTEGER(0..7)

PRSResourceSet-List ::= SEQUENCE (SIZE (1.. maxnoofPRSresourceSets)) OF PRSResourceSet-Item
PRSResourceSet-Item ::= SEQUENCE {
	pRSResourceSetID				PRS-Resource-Set-ID,
	subcarrierSpacing				ENUMERATED{kHz15, kHz30, kHz60, kHz120, ...},
	pRSbandwidth					INTEGER(1..63),
	startPRB						INTEGER(0..2176),
	pointA							INTEGER (0..3279165),
	combSize						ENUMERATED{n2, n4, n6, n12, ...},
	cPType							ENUMERATED{normal, extended, ...},
	resourceSetPeriodicity			ENUMERATED{n4,n5,n8,n10,n16,n20,n32,n40,n64,n80,n160,n320,n640,n1280,n2560,n5120,n10240,n20480,n40960, n81920,...},
	resourceSetSlotOffset			INTEGER(0..81919,...),
	resourceRepetitionFactor		ENUMERATED{rf1,rf2,rf4,rf6,rf8,rf16,rf32,...},
	resourceTimeGap					ENUMERATED{tg1,tg2,tg4,tg8,tg16,tg32,...},
	resourceNumberofSymbols			ENUMERATED{n2,n4,n6,n12,...},
	pRSMuting						PRSMuting 		OPTIONAL,
	pRSResourceTransmitPower		INTEGER(-60..50),
	pRSResource-List				PRSResource-List,
	iE-Extensions					ProtocolExtensionContainer { { PRSResourceSet-Item-ExtIEs} } OPTIONAL
}

PRSResourceSet-Item-ExtIEs F1AP-PROTOCOL-EXTENSION ::= {
	...
}

PRSTransmissionOffIndication ::= CHOICE {
	pRSTransmissionOffPerTRP				NULL,
	pRSTransmissionOffPerResourceSet		PRSTransmissionOffPerResourceSet,
	pRSTransmissionOffPerResource			PRSTransmissionOffPerResource,
	choice-extension		ProtocolIE-SingleContainer { { PRSTransmissionOffIndication-ExtIEs } }
}

PRSTransmissionOffIndication-ExtIEs F1AP-PROTOCOL-IES ::= {
	...
}

PRSTransmissionOffPerResource ::= SEQUENCE (SIZE (1..maxnoofPRSresourceSets)) OF PRSTransmissionOffPerResource-Item

PRSTransmissionOffPerResource-Item  ::= SEQUENCE {
	pRSResourceSetID								PRS-Resource-Set-ID,
	pRSTransmissionOffIndicationPerResourceList		SEQUENCE (SIZE(1.. maxnoofPRSresources)) OF PRSTransmissionOffIndicationPerResource-Item,
	iE-Extensions		ProtocolExtensionContainer { { PRSTransmissionOffPerResource-Item-ExtIEs } } OPTIONAL,
	...
}

PRSTransmissionOffPerResource-Item-ExtIEs F1AP-PROTOCOL-EXTENSION ::= {
	...
}

PRSTransmissionOffIndicationPerResource-Item  ::= SEQUENCE {
	pRSResourceID		PRS-Resource-ID,
	iE-Extensions		ProtocolExtensionContainer { { PRSTransmissionOffIndicationPerResource-Item-ExtIEs } } OPTIONAL,
	...
}

PRSTransmissionOffIndicationPerResource-Item-ExtIEs F1AP-PROTOCOL-EXTENSION ::= {
	...
}

PRSTransmissionOffInformation ::= SEQUENCE {
	pRSTransmissionOffIndication	PRSTransmissionOffIndication,
	iE-Extensions					ProtocolExtensionContainer { { PRSTransmissionOffInformation-ExtIEs } } OPTIONAL,
	...
}

PRSTransmissionOffInformation-ExtIEs F1AP-PROTOCOL-EXTENSION ::= {
	...
}

PRSTransmissionOffPerResourceSet ::= SEQUENCE (SIZE (1..maxnoofPRSresourceSets)) OF PRSTransmissionOffPerResourceSet-Item

PRSTransmissionOffPerResourceSet-Item  ::= SEQUENCE {
	pRSResourceSetID		PRS-Resource-Set-ID,
	iE-Extensions			ProtocolExtensionContainer { { PRSTransmissionOffPerResourceSet-Item-ExtIEs } } OPTIONAL,
	...
}

PRSTransmissionOffPerResourceSet-Item-ExtIEs F1AP-PROTOCOL-EXTENSION ::= {
	...
}


PWS-Failed-NR-CGI-Item ::= SEQUENCE {
	nRCGI				NRCGI,
	numberOfBroadcasts	NumberOfBroadcasts,
	iE-Extensions		ProtocolExtensionContainer { { PWS-Failed-NR-CGI-ItemExtIEs } }	OPTIONAL,
	...
}

PWS-Failed-NR-CGI-ItemExtIEs 	F1AP-PROTOCOL-EXTENSION ::= {
	...
}

PWSSystemInformation ::= SEQUENCE {
	sIBtype 				SIBType-PWS,
	sIBmessage				OCTET STRING,
	iE-Extensions			ProtocolExtensionContainer { { PWSSystemInformationExtIEs } }	OPTIONAL,
	...
}

PWSSystemInformationExtIEs 	F1AP-PROTOCOL-EXTENSION ::= {
	{ID id-NotificationInformation		CRITICALITY ignore	EXTENSION NotificationInformation		PRESENCE optional}|
	{ ID id-AdditionalSIBMessageList	CRITICALITY reject	EXTENSION AdditionalSIBMessageList		PRESENCE optional},
	...
}

PrivacyIndicator ::= ENUMERATED {immediate-MDT,	logged-MDT,	...}

PRS-ID ::= INTEGER(0..255)

PRSTRPList ::= SEQUENCE (SIZE(1.. maxnoofTRPs)) OF PRSTRPItem

PRSTRPItem ::= SEQUENCE {
	tRP-ID		TRPID,
	requestedDLPRSTransmissionCharacteristics	RequestedDLPRSTransmissionCharacteristics 		OPTIONAL,
	-- The IE shall be present if the PRS Configuration Request Type IE is set to "configure" --
	pRSTransmissionOffInformation		PRSTransmissionOffInformation				OPTIONAL,
	-- The IE shall be present if the PRS Configuration Request Type IE is set to "off" --

	iE-Extensions	ProtocolExtensionContainer { { PRSTRPItem-ExtIEs} } OPTIONAL,
	...
}

PRSTRPItem-ExtIEs F1AP-PROTOCOL-EXTENSION ::= {
	...
}

RequestedDLPRSTransmissionCharacteristics ::= SEQUENCE {
	requestedDLPRSResourceSet-List		RequestedDLPRSResourceSet-List,
	numberofFrequencyLayers			INTEGER(1..4)										OPTIONAL,
	startTimeAndDuration			StartTimeAndDuration								OPTIONAL,
	iE-Extensions	ProtocolExtensionContainer { { RequestedDLPRSTransmissionCharacteristics-ExtIEs} } OPTIONAL,
	...
}
RequestedDLPRSTransmissionCharacteristics-ExtIEs F1AP-PROTOCOL-EXTENSION ::= {
	...
}

RequestedDLPRSResourceSet-List ::= SEQUENCE (SIZE (1..maxnoofPRSresourceSets)) OF RequestedDLPRSResourceSet-Item

RequestedDLPRSResourceSet-Item ::= SEQUENCE {
	pRSbandwidth					INTEGER(1..63),
	combSize						ENUMERATED{n2, n4, n6, n12, ...}		OPTIONAL,
	resourceSetPeriodicity			ENUMERATED{n4,n5,n8,n10,n16,n20,n32,n40,n64,n80,n160,n320,n640,n1280,n2560,n5120,n10240,n20480,n40960, n81920,...}	OPTIONAL,
	resourceRepetitionFactor		ENUMERATED{rf1,rf2,rf4,rf6,rf8,rf16,rf32,...}		OPTIONAL,
	resourceNumberofSymbols			ENUMERATED{n2,n4,n6,n12,...}						OPTIONAL,
	requestedDLPRSResource-List		RequestedDLPRSResource-List							OPTIONAL,
	resourceSetStartTimeAndDuration	StartTimeAndDuration								OPTIONAL,
	iE-Extensions					ProtocolExtensionContainer { { RequestedDLPRSResourceSet-Item-ExtIEs} } OPTIONAL,
	...
}

RequestedDLPRSResourceSet-Item-ExtIEs F1AP-PROTOCOL-EXTENSION ::= {
	...
}

RequestedDLPRSResource-List::= SEQUENCE (SIZE (1..maxnoofPRSresources)) OF RequestedDLPRSResource-Item

RequestedDLPRSResource-Item  ::= SEQUENCE {
	qCLInfo					PRSResource-QCLInfo		OPTIONAL,
	iE-Extensions			ProtocolExtensionContainer { { RequestedDLPRSResource-Item-ExtIEs} } OPTIONAL,
	...
}

RequestedDLPRSResource-Item-ExtIEs F1AP-PROTOCOL-EXTENSION ::= {
	...
}


PRSTransmissionTRPList ::= SEQUENCE (SIZE(1.. maxnoofTRPs)) OF PRSTransmissionTRPItem

PRSTransmissionTRPItem ::= SEQUENCE {
		tRP-ID				TRPID,
		pRSConfiguration	PRSConfiguration,
	iE-Extensions			ProtocolExtensionContainer { { PRSTransmissionTRPItem-ExtIEs} } OPTIONAL,
		...
}

PRSTransmissionTRPItem-ExtIEs F1AP-PROTOCOL-EXTENSION ::= {
	...
}


-- Q

QCI ::= INTEGER (0..255)

QoEInformation ::= SEQUENCE {
	qoEInformationList		QoEInformationList,
	iE-Extensions			ProtocolExtensionContainer { { QoEInformation-ExtIEs} } OPTIONAL
}

QoEInformation-ExtIEs 	F1AP-PROTOCOL-EXTENSION ::= {
	...
}

QoEInformationList ::= SEQUENCE (SIZE(1.. maxnoofQoEInformation)) OF QoEInformationList-Item

QoEInformationList-Item ::= SEQUENCE {
	qoEMetrics			QoEMetrics	OPTIONAL,
	iE-Extensions		ProtocolExtensionContainer { { QoEInformationList-Item-ExtIEs} } 	OPTIONAL
}

QoEInformationList-Item-ExtIEs 	F1AP-PROTOCOL-EXTENSION ::= {
	...
}

QoEMetrics ::= SEQUENCE {
	appLayerBufferLevelList				AppLayerBufferLevelList  OPTIONAL,
	playoutDelayForMediaStartup			PlayoutDelayForMediaStartup OPTIONAL,
	iE-Extensions						ProtocolExtensionContainer { { QoEMetrics-ExtIEs} } OPTIONAL,
	...
}

QoEMetrics-ExtIEs 	F1AP-PROTOCOL-EXTENSION ::= {
	...
}

QoS-Characteristics ::= CHOICE {
	non-Dynamic-5QI				NonDynamic5QIDescriptor,
	dynamic-5QI					Dynamic5QIDescriptor,
	choice-extension			ProtocolIE-SingleContainer { { QoS-Characteristics-ExtIEs } }
}

QoS-Characteristics-ExtIEs F1AP-PROTOCOL-IES ::= {
	...
}

QoSFlowIdentifier ::= INTEGER (0..63)

QoSFlowLevelQoSParameters	::= SEQUENCE {
	qoS-Characteristics						QoS-Characteristics,
	nGRANallocationRetentionPriority		NGRANAllocationAndRetentionPriority,
	gBR-QoS-Flow-Information				GBR-QoSFlowInformation				OPTIONAL,
	reflective-QoS-Attribute				ENUMERATED {subject-to, ...}				OPTIONAL,
	iE-Extensions							ProtocolExtensionContainer { { QoSFlowLevelQoSParameters-ExtIEs } }	OPTIONAL
}

QoSFlowLevelQoSParameters-ExtIEs 	F1AP-PROTOCOL-EXTENSION ::= {
	{ ID id-PDUSessionID								CRITICALITY ignore	EXTENSION PDUSessionID				PRESENCE optional}|
	{ ID id-ULPDUSessionAggregateMaximumBitRate			CRITICALITY ignore	EXTENSION BitRate						PRESENCE optional}|
	{ ID id-QosMonitoringRequest						CRITICALITY ignore	EXTENSION QosMonitoringRequest		PRESENCE optional}|
	{ ID id-PDCPTerminatingNodeDLTNLAddrInfo			CRITICALITY ignore	EXTENSION TransportLayerAddress	PRESENCE optional	},
	...
}

QoSFlowMappingIndication ::= ENUMERATED {ul,dl,...}

QoSInformation	::=	CHOICE {
	eUTRANQoS					EUTRANQoS,
	choice-extension			ProtocolIE-SingleContainer { { QoSInformation-ExtIEs} }
}

QoSInformation-ExtIEs F1AP-PROTOCOL-IES ::= {
	{	ID id-DRB-Information		CRITICALITY ignore TYPE DRB-Information		PRESENCE mandatory},
	...
}

QosMonitoringRequest ::= ENUMERATED {ul, dl, both, ..., stop}

QoSParaSetIndex ::= INTEGER (1..8, ...)

QoSParaSetNotifyIndex ::= INTEGER (0..8, ...)

-- R

RACH-Config-Common	::= OCTET STRING

RACH-Config-Common-IAB	::= OCTET STRING

RACHReportContainer::= OCTET STRING

RACHReportInformationList	::= SEQUENCE (SIZE(1.. maxnoofRACHReports)) OF RACHReportInformationItem

RACHReportInformationItem	::= SEQUENCE {
	rACHReportContainer				RACHReportContainer,
	uEAssitantIdentifier			GNB-DU-UE-F1AP-ID		OPTIONAL,
	iE-Extensions					ProtocolExtensionContainer { { RACHReportInformationItem-ExtIEs} }	OPTIONAL,
	...
}

RACHReportInformationItem-ExtIEs 	F1AP-PROTOCOL-EXTENSION ::= {
	...
}



RadioResourceStatus ::= SEQUENCE {
	sSBAreaRadioResourceStatusList		SSBAreaRadioResourceStatusList,
	iE-Extensions	ProtocolExtensionContainer { { RadioResourceStatus-ExtIEs} } OPTIONAL
}

RadioResourceStatus-ExtIEs 	F1AP-PROTOCOL-EXTENSION ::= {
	{ ID id-SliceRadioResourceStatus		CRITICALITY ignore	EXTENSION SliceRadioResourceStatus		PRESENCE optional	}|
	{ ID id-MIMOPRBusageInformation			CRITICALITY ignore	EXTENSION MIMOPRBusageInformation			PRESENCE optional	},
	...
}

MIMOPRBusageInformation ::= SEQUENCE {
	dl-GBR-PRB-usage-for-MIMO		INTEGER (0..100),
	ul-GBR-PRB-usage-for-MIMO		INTEGER (0..100),
	dl-non-GBR-PRB-usage-for-MIMO	INTEGER (0..100),
	ul-non-GBR-PRB-usage-for-MIMO 	INTEGER (0..100),
	dl-Total-PRB-usage-for-MIMO 	INTEGER (0..100),
	ul-Total-PRB-usage-for-MIMO 	INTEGER (0..100),
	iE-Extensions					ProtocolExtensionContainer { { MIMOPRBusageInformation-ExtIEs} }	OPTIONAL,
	...
}

MIMOPRBusageInformation-ExtIEs F1AP-PROTOCOL-EXTENSION ::= {
	...
}

RANAC ::= INTEGER (0..255)

RAN-MeasurementID ::= INTEGER (1.. 65536, ...)

RAN-UE-MeasurementID ::= INTEGER (1.. 256, ...)

RAN-UE-PDC-MeasID ::= INTEGER (1..16, ...)

RANUEID ::= OCTET STRING (SIZE (8))

RANUEPagingIdentity ::= SEQUENCE	{
	iRNTI						BIT STRING (SIZE(40)),
	iE-Extensions				ProtocolExtensionContainer { { RANUEPagingIdentity-ExtIEs } }	OPTIONAL}

RANUEPagingIdentity-ExtIEs 	F1AP-PROTOCOL-EXTENSION ::= {
	...
}

RAT-FrequencyPriorityInformation::= CHOICE {
	eNDC		SubscriberProfileIDforRFP,
	nGRAN		RAT-FrequencySelectionPriority,
	choice-extension			ProtocolIE-SingleContainer { { RAT-FrequencyPriorityInformation-ExtIEs} }
}

RAT-FrequencyPriorityInformation-ExtIEs F1AP-PROTOCOL-IES ::= {
	...
}

RAT-FrequencySelectionPriority::= INTEGER (1.. 256, ...)

RBSetConfiguration ::= SEQUENCE {
	subcarrierSpacing				SubcarrierSpacing,
	rBSetSize						RBSetSize,
	nUmberRBsets					INTEGER(1..maxnoofRBsetsPerCell),
	iE-Extensions					ProtocolExtensionContainer { { RBSetConfiguration-ExtIEs} } OPTIONAL
}

RBSetConfiguration-ExtIEs F1AP-PROTOCOL-EXTENSION ::= {
	...
}

RBSetSize ::=	ENUMERATED { rb2, rb4, rb8, rb16, rb32, rb64}



Re-routingEnableIndicator ::= ENUMERATED {
	true,
	false,
	...
}

Redcap-Bcast-Information ::= BIT STRING(SIZE(8))

RedCapIndication ::= ENUMERATED {true, ...}

Reestablishment-Indication	::=	ENUMERATED  {
	reestablished,
	...
}

ReferencePoint ::= CHOICE {
	coordinateID					CoordinateID,
	referencePointCoordinate		AccessPointPosition,
	referencePointCoordinateHA		NGRANHighAccuracyAccessPointPosition,
	choice-Extension				ProtocolIE-SingleContainer { { ReferencePoint-ExtIEs} }
}

ReferencePoint-ExtIEs F1AP-PROTOCOL-IES ::= {
	...
}

ReferenceSFN ::= INTEGER (0..1023)

ReferenceSignal ::= CHOICE {
	nZP-CSI-RS								NZP-CSI-RS-ResourceID,
	sSB										SSB,
	sRS										SRSResourceID,
	positioningSRS							SRSPosResourceID,
	dL-PRS									DL-PRS,
	choice-extension						ProtocolIE-SingleContainer {{ReferenceSignal-ExtIEs }}
}

ReferenceSignal-ExtIEs F1AP-PROTOCOL-IES ::= {
	...
}

RelativeCartesianLocation ::= SEQUENCE {
	xYZunit						ENUMERATED {mm, cm, dm, ...},
	xvalue						INTEGER (-65536..65535),
	yvalue						INTEGER (-65536..65535),
	zvalue						INTEGER (-32768..32767),
	locationUncertainty			LocationUncertainty,
	iE-Extensions				ProtocolExtensionContainer { { RelativeCartesianLocation-ExtIEs} } OPTIONAL
}

RelativeCartesianLocation-ExtIEs F1AP-PROTOCOL-EXTENSION ::= {
	...
}

RelativeGeodeticLocation ::= SEQUENCE {
	milli-Arc-SecondUnits		ENUMERATED {zerodot03, zerodot3, three, ...},
	heightUnits					ENUMERATED {mm, cm, m, ...},
	deltaLatitude				INTEGER (-1024.. 1023),
	deltaLongitude				INTEGER (-1024.. 1023),
	deltaHeight					INTEGER (-1024.. 1023),
	locationUncertainty			LocationUncertainty,
	iE-extensions				ProtocolExtensionContainer {{RelativeGeodeticLocation-ExtIEs }} OPTIONAL
}

RelativeGeodeticLocation-ExtIEs F1AP-PROTOCOL-EXTENSION ::= {
	...
}

RemoteUELocalID ::= INTEGER (0..255, ...)


ReferenceTime ::= OCTET STRING

RegistrationRequest ::= ENUMERATED{start, stop, add, ...}

ReportCharacteristics ::= BIT STRING (SIZE(32))

ReportingPeriodicity ::= ENUMERATED{ms500, ms1000, ms2000, ms5000, ms10000, ...}

RequestedBandCombinationIndex ::= OCTET STRING

RequestedFeatureSetEntryIndex ::= OCTET STRING

RequestedP-MaxFR2 ::= OCTET STRING

Requested-PDCCH-BlindDetectionSCG ::= OCTET STRING


RequestedSRSTransmissionCharacteristics ::= SEQUENCE {
	numberOfTransmissions		INTEGER (0..500, ...)		OPTIONAL,
-- The IE shall be present if the Resource Type IE is set to "periodic" --
	resourceType				ENUMERATED  {periodic, semi-persistent, aperiodic,...},
	bandwidthSRS				BandwidthSRS,
	sRSResourceSetList 			SRSResourceSetList				OPTIONAL,
	sSBInformation				SSBInformation				OPTIONAL,
	iE-Extensions			ProtocolExtensionContainer { { RequestedSRSTransmissionCharacteristics-ExtIEs} } OPTIONAL
}

RequestedSRSTransmissionCharacteristics-ExtIEs F1AP-PROTOCOL-EXTENSION ::= {
	{ ID id-SrsFrequency		CRITICALITY ignore EXTENSION SrsFrequency		PRESENCE optional },
	...
}


RequestType	::= ENUMERATED {offer, execution, ...}

ResourceCoordinationEUTRACellInfo ::= SEQUENCE {
	eUTRA-Mode-Info 						EUTRA-Coex-Mode-Info,
	eUTRA-PRACH-Configuration 				EUTRA-PRACH-Configuration,
	iE-Extensions	ProtocolExtensionContainer { { ResourceCoordinationEUTRACellInfo-ExtIEs } }	OPTIONAL,
	...
}

ResourceCoordinationEUTRACellInfo-ExtIEs 	F1AP-PROTOCOL-EXTENSION ::= {
	{ID id-IgnorePRACHConfiguration		CRITICALITY reject EXTENSION IgnorePRACHConfiguration		PRESENCE optional },
	...
}

ResourceCoordinationTransferInformation ::= SEQUENCE {
	meNB-Cell-ID								EUTRA-Cell-ID,
	resourceCoordinationEUTRACellInfo		ResourceCoordinationEUTRACellInfo	OPTIONAL,
	iE-Extensions	ProtocolExtensionContainer { { ResourceCoordinationTransferInformation-ExtIEs } }	OPTIONAL,
	...
}

ResourceCoordinationTransferInformation-ExtIEs 	F1AP-PROTOCOL-EXTENSION ::= {
	...
}

ResourceCoordinationTransferContainer ::= OCTET STRING

ResourceSetType  ::= CHOICE {
	periodic			ResourceSetTypePeriodic,
	semi-persistent		ResourceSetTypeSemi-persistent,
	aperiodic			ResourceSetTypeAperiodic,
	choice-extension				ProtocolIE-SingleContainer {{ ResourceSetType-ExtIEs }}
}

ResourceSetType-ExtIEs F1AP-PROTOCOL-IES ::= {
	...
}

ResourceSetTypePeriodic ::= SEQUENCE {
	periodicSet			ENUMERATED{true, ...},
	iE-Extensions		ProtocolExtensionContainer { { ResourceSetTypePeriodic-ExtIEs} }	OPTIONAL
}

ResourceSetTypePeriodic-ExtIEs F1AP-PROTOCOL-EXTENSION ::= {
	...
}

ResourceSetTypeSemi-persistent ::= SEQUENCE {
	semi-persistentSet	ENUMERATED{true, ...},
	iE-Extensions		ProtocolExtensionContainer { { ResourceSetTypeSemi-persistent-ExtIEs} }	OPTIONAL
}

ResourceSetTypeSemi-persistent-ExtIEs F1AP-PROTOCOL-EXTENSION ::= {
	...
}

ResourceSetTypeAperiodic ::= SEQUENCE {
	sRSResourceTrigger-List 	INTEGER(1..3),
	slotoffset					INTEGER(0..32),
	iE-Extensions				ProtocolExtensionContainer { { ResourceSetTypeAperiodic-ExtIEs} }	OPTIONAL
}

ResourceSetTypeAperiodic-ExtIEs F1AP-PROTOCOL-EXTENSION ::= {
	...
}

RepetitionPeriod ::= INTEGER (0..131071, ...)

ReportingRequestType ::= SEQUENCE {
	eventType						EventType,
	reportingPeriodicityValue						ReportingPeriodicityValue		OPTIONAL,
	-- C-ifEventTypeisPeriodic: This IE shall be present if the Event Type IE is set to "periodic" in the Event Type IE.
	iE-Extensions					ProtocolExtensionContainer { {ReportingRequestType-ExtIEs} }	OPTIONAL
}

ReportingRequestType-ExtIEs F1AP-PROTOCOL-EXTENSION ::= {
	...
}

ResourceType ::= CHOICE {
	periodic			ResourceTypePeriodic,
	semi-persistent		ResourceTypeSemi-persistent,
	aperiodic			ResourceTypeAperiodic,
	choice-extension				ProtocolIE-SingleContainer {{ ResourceType-ExtIEs }}
}

ResourceType-ExtIEs F1AP-PROTOCOL-IES ::= {
	...
}

ResourceTypePeriodic ::= SEQUENCE {
	periodicity		   ENUMERATED{slot1, slot2, slot4, slot5, slot8, slot10, slot16, slot20, slot32, slot40, slot64, slot80, slot160, slot320, slot640, slot1280, slot2560, ...},
	offset				INTEGER(0..2559, ...),
	iE-Extensions		ProtocolExtensionContainer { { ResourceTypePeriodic-ExtIEs} }	OPTIONAL
}

ResourceTypePeriodic-ExtIEs F1AP-PROTOCOL-EXTENSION ::= {
	...
}

ResourceTypeSemi-persistent ::= SEQUENCE {
	periodicity		   ENUMERATED{slot1, slot2, slot4, slot5, slot8, slot10, slot16, slot20, slot32, slot40, slot64, slot80, slot160, slot320, slot640, slot1280, slot2560, ...},
	offset				INTEGER(0..2559, ...),
	iE-Extensions		ProtocolExtensionContainer { { ResourceTypeSemi-persistent-ExtIEs} }	OPTIONAL
}

ResourceTypeSemi-persistent-ExtIEs F1AP-PROTOCOL-EXTENSION ::= {
	...
}

ResourceTypeAperiodic ::= SEQUENCE {
	aperiodicResourceType	   ENUMERATED{true, ...},
	iE-Extensions		ProtocolExtensionContainer { { ResourceTypeAperiodic-ExtIEs} }	OPTIONAL
}

ResourceTypeAperiodic-ExtIEs F1AP-PROTOCOL-EXTENSION ::= {
	...
}

ResourceTypePos ::= CHOICE {
	periodic			ResourceTypePeriodicPos,
	semi-persistent		ResourceTypeSemi-persistentPos,
	aperiodic			ResourceTypeAperiodicPos,
	choice-extension	ProtocolIE-SingleContainer {{ ResourceTypePos-ExtIEs }}
}

ResourceTypePos-ExtIEs F1AP-PROTOCOL-IES ::= {
	...
}

ResourceTypePeriodicPos ::= SEQUENCE {
	periodicity			ENUMERATED{slot1, slot2, slot4, slot5, slot8, slot10, slot16, slot20, slot32, slot40, slot64, slot80, slot160, slot320, slot640, slot1280, slot2560, slot5120, slot10240, slot40960, slot81920, ..., slot128, slot256, slot512, slot20480},
	offset				INTEGER(0..81919, ...),
	iE-Extensions		ProtocolExtensionContainer { { ResourceTypePeriodicPos-ExtIEs} }	OPTIONAL
}

ResourceTypePeriodicPos-ExtIEs F1AP-PROTOCOL-EXTENSION ::= {
	...
}

ResourceTypeSemi-persistentPos ::= SEQUENCE {
	periodicity			ENUMERATED{slot1, slot2, slot4, slot5, slot8, slot10, slot16, slot20, slot32, slot40, slot64, slot80, slot160, slot320, slot640, slot1280, slot2560, slot5120, slot10240, slot40960, slot81920, ..., slot128, slot256, slot512, slot20480},
	offset				INTEGER(0..81919, ...),
	iE-Extensions		ProtocolExtensionContainer { { ResourceTypeSemi-persistentPos-ExtIEs} }	OPTIONAL
}

ResourceTypeSemi-persistentPos-ExtIEs F1AP-PROTOCOL-EXTENSION ::= {
	...
}

ResourceTypeAperiodicPos ::= SEQUENCE {
	slotOffset			INTEGER (0..32),
	iE-Extensions		ProtocolExtensionContainer { { ResourceTypeAperiodicPos-ExtIEs} }	OPTIONAL
}

ResourceTypeAperiodicPos-ExtIEs F1AP-PROTOCOL-EXTENSION ::= {
	...
}

RLCDuplicationInformation ::= SEQUENCE {
	rLCDuplicationStateList 			RLCDuplicationStateList,
	primaryPathIndication			PrimaryPathIndication	OPTIONAL,
	iE-Extensions					ProtocolExtensionContainer { {RLCDuplicationInformation-ExtIEs} }	OPTIONAL
}

RLCDuplicationInformation-ExtIEs 	F1AP-PROTOCOL-EXTENSION ::= {
	...
}

RLCDuplicationStateList	::= SEQUENCE (SIZE(1..maxnoofRLCDuplicationState)) OF RLCDuplicationState-Item

RLCDuplicationState-Item ::=SEQUENCE {
	duplicationState		DuplicationState,
	iE-Extensions	ProtocolExtensionContainer { {RLCDuplicationState-Item-ExtIEs } }	OPTIONAL,
	...
}


RLCDuplicationState-Item-ExtIEs 	F1AP-PROTOCOL-EXTENSION ::= {
	...
}

RLCFailureIndication ::= SEQUENCE {
	assocatedLCID				LCID,
	iE-Extensions				ProtocolExtensionContainer { {RLCFailureIndication-ExtIEs} } OPTIONAL
}

RLCFailureIndication-ExtIEs F1AP-PROTOCOL-EXTENSION ::= {
	...
}

RLCMode ::= ENUMERATED {
	rlc-am,
	rlc-um-bidirectional,
	rlc-um-unidirectional-ul,
	rlc-um-unidirectional-dl,
	...
}

RLC-Status ::= SEQUENCE {
	reestablishment-Indication 	Reestablishment-Indication,
	iE-Extensions				ProtocolExtensionContainer { { RLC-Status-ExtIEs } } OPTIONAL,
	...
}

RLC-Status-ExtIEs F1AP-PROTOCOL-EXTENSION ::= {
	...
}

RLFReportInformationList	::= SEQUENCE (SIZE(1.. maxnoofRLFReports)) OF RLFReportInformationItem

RLFReportInformationItem	::= SEQUENCE {
	nRUERLFReportContainer		NRUERLFReportContainer,
	uEAssitantIdentifier		GNB-DU-UE-F1AP-ID		OPTIONAL,
	iE-Extensions				ProtocolExtensionContainer { { RLFReportInformationItem-ExtIEs} }	OPTIONAL,
	...
}

RLFReportInformationItem-ExtIEs 	F1AP-PROTOCOL-EXTENSION ::= {
	...
}

RIMRSDetectionStatus ::= ENUMERATED {rs-detected, rs-disappeared, ...}

RRCContainer ::= OCTET STRING

RRCContainer-RRCSetupComplete ::= OCTET STRING

RRCDeliveryStatus ::= SEQUENCE	{
	delivery-status 			PDCP-SN,
	triggering-message			PDCP-SN,
	iE-Extensions				ProtocolExtensionContainer { { RRCDeliveryStatus-ExtIEs } }	OPTIONAL}

RRCDeliveryStatus-ExtIEs 	F1AP-PROTOCOL-EXTENSION ::= {
	...
}


RRCDeliveryStatusRequest ::= ENUMERATED {true, ...}

RRCReconfigurationCompleteIndicator	::= ENUMERATED {
	true,
	 ...,
	failure
}

RRC-Version ::= SEQUENCE	{
	latest-RRC-Version			BIT STRING (SIZE(3)),
	iE-Extensions				ProtocolExtensionContainer { { RRC-Version-ExtIEs } }	OPTIONAL}

RRC-Version-ExtIEs 	F1AP-PROTOCOL-EXTENSION ::= {
	{ID id-latest-RRC-Version-Enhanced		CRITICALITY ignore EXTENSION OCTET STRING (SIZE(3))		PRESENCE optional },
	...
}

RoutingID ::= OCTET STRING

ResponseTime ::= SEQUENCE {
	time      			INTEGER (1..128,...),
	timeUnit	ENUMERATED {second, ten-seconds, ten-milliseconds,...},
	iE-Extensions		ProtocolExtensionContainer { { ResponseTime-ExtIEs} }	OPTIONAL,
	...
}

ResponseTime-ExtIEs F1AP-PROTOCOL-EXTENSION ::= {
	...
}

RxTxTimingErrorMargin ::= ENUMERATED {tc0dot5, tc1, tc2, tc4, tc8, tc12, tc16, tc20, tc24, tc32, tc40, tc48, tc64, tc80, tc96, tc128, ...}

-- S

SCell-FailedtoSetup-Item	::= SEQUENCE {
	sCell-ID			NRCGI	,
	cause		Cause			OPTIONAL ,
	iE-Extensions	ProtocolExtensionContainer { { SCell-FailedtoSetup-ItemExtIEs } }	OPTIONAL,
	...
}

SCell-FailedtoSetup-ItemExtIEs 	F1AP-PROTOCOL-EXTENSION ::= {
	...
}

SCell-FailedtoSetupMod-Item	::= SEQUENCE {
	sCell-ID			NRCGI	,
	cause		Cause			OPTIONAL ,
	iE-Extensions	ProtocolExtensionContainer { { SCell-FailedtoSetupMod-ItemExtIEs } }	OPTIONAL,
	...
}

SCell-FailedtoSetupMod-ItemExtIEs 	F1AP-PROTOCOL-EXTENSION ::= {
	...
}

SCell-ToBeRemoved-Item	::= SEQUENCE {
	sCell-ID			NRCGI	,
	iE-Extensions	ProtocolExtensionContainer { { SCell-ToBeRemoved-ItemExtIEs } }	OPTIONAL,
	...
}

SCell-ToBeRemoved-ItemExtIEs 	F1AP-PROTOCOL-EXTENSION ::= {
	...
}

SCell-ToBeSetup-Item ::= SEQUENCE {
	sCell-ID			NRCGI	,
	sCellIndex			SCellIndex,
	sCellULConfigured		CellULConfigured 	OPTIONAL,
	iE-Extensions	ProtocolExtensionContainer { { SCell-ToBeSetup-ItemExtIEs } }	OPTIONAL,
	...
}

SCell-ToBeSetup-ItemExtIEs 	F1AP-PROTOCOL-EXTENSION ::= {
	{ ID id-ServingCellMO		CRITICALITY ignore	EXTENSION ServingCellMO		PRESENCE optional	},
	...
}

SCell-ToBeSetupMod-Item	::= SEQUENCE {
	sCell-ID			NRCGI	,
	sCellIndex			SCellIndex,
	sCellULConfigured		CellULConfigured 	OPTIONAL,
	iE-Extensions	ProtocolExtensionContainer { { SCell-ToBeSetupMod-ItemExtIEs } }	OPTIONAL,
	...
}

SCell-ToBeSetupMod-ItemExtIEs 	F1AP-PROTOCOL-EXTENSION ::= {
	{ ID id-ServingCellMO		CRITICALITY ignore	EXTENSION ServingCellMO		PRESENCE optional	},
	...
}

SCellIndex ::=INTEGER (1..31, ...)

SCGActivationRequest ::= ENUMERATED {activate-scg, deactivate-scg, ...}

SCGActivationStatus ::= ENUMERATED {scg-activated, scg-deactivated, ...}

SCGIndicator	::=	ENUMERATED{released, ...}

SCS-480	::= INTEGER(0..319)

SCS-960	::= INTEGER(0..639)

SCS-SpecificCarrier ::=					SEQUENCE {
    offsetToCarrier						INTEGER (0..2199,...),
    subcarrierSpacing					ENUMERATED {kHz15, kHz30, kHz60, kHz120,..., kHz480, kHz960},
    carrierBandwidth					INTEGER (1..275,...),
	iE-Extensions						ProtocolExtensionContainer { { SCS-SpecificCarrier-ExtIEs } } OPTIONAL
}

SCS-SpecificCarrier-ExtIEs F1AP-PROTOCOL-EXTENSION ::= {
	...
}

SDTBearerConfigurationQueryIndication ::=	ENUMERATED {true, ...}

SDTBearerConfigurationInfo ::= SEQUENCE {
	sDTBearerConfig-List			SDTBearerConfig-List,
	iE-Extensions					ProtocolExtensionContainer { { SDTBearerConfigurationInfo-ExtIEs } } OPTIONAL
}

SDTBearerConfigurationInfo-ExtIEs F1AP-PROTOCOL-EXTENSION ::= {
	...
}

SDTBearerConfig-List ::= SEQUENCE (SIZE(1..maxnoofSDTBearers)) OF SDTBearerConfig-List-Item

SDTBearerConfig-List-Item ::= SEQUENCE{
	sDTBearerType 							SDTBearerType,
	sDTRLCBearerConfiguration				SDTRLCBearerConfiguration,
	iE-Extensions			ProtocolExtensionContainer {{ SDTBearerConfig-List-Item-ExtIEs}}		OPTIONAL
}

SDTBearerConfig-List-Item-ExtIEs 	F1AP-PROTOCOL-EXTENSION ::= {
	...
}

SDTBearerType ::= CHOICE {
	sRB					SRBID,
	dRB					DRBID,
	choice-extension				ProtocolIE-SingleContainer {{ SDTBearerType-ExtIEs }}
}

SDTBearerType-ExtIEs F1AP-PROTOCOL-IES ::= {
	...
}

SDT-MAC-PHY-CG-Config ::= OCTET STRING

SDTInformation ::= SEQUENCE {
	sdtIndicator					ENUMERATED {true,...},
	sdtAssistantInformation			ENUMERATED {singlepacket, multiplepackets,...}	OPTIONAL,
	iE-Extensions					ProtocolExtensionContainer { { SDTInformation-ExtIEs } } OPTIONAL
}

SDTInformation-ExtIEs F1AP-PROTOCOL-EXTENSION ::= {
	...
}

SDTRLCBearerConfiguration ::= OCTET STRING

SDT-Termination-Request	::= ENUMERATED {radio-link-problem, normal, ...}


Search-window-information ::= SEQUENCE {
	expectedPropagationDelay		INTEGER (-3841..3841,...),
	delayUncertainty				INTEGER (1..246,...),
	iE-Extensions					ProtocolExtensionContainer { { Search-window-information-ExtIEs } } OPTIONAL
}

Search-window-information-ExtIEs F1AP-PROTOCOL-EXTENSION ::= {
	...
}

SerialNumber ::= BIT STRING (SIZE (16))

SIBType-PWS ::=INTEGER (6..8, ...)

SelectedBandCombinationIndex ::= OCTET STRING

SelectedFeatureSetEntryIndex ::= OCTET STRING

CG-ConfigInfo ::= OCTET STRING

ServCellIndex ::= INTEGER (0..31, ...)

ServingCellMO ::= INTEGER (1..64, ...)

ServingCellMO-List-Item ::= SEQUENCE {
	servingCellMO					ServingCellMO,
	sSB-Frequency					INTEGER (0..3279165),
	iE-Extensions					ProtocolExtensionContainer { { ServingCellMO-List-Item-ExtIEs } } OPTIONAL
}

ServingCellMO-List-Item-ExtIEs F1AP-PROTOCOL-EXTENSION ::= {
	...
}

ServingCellMO-encoded-in-CGC-List ::= SEQUENCE (SIZE(1.. maxNrofBWPs)) OF ServingCellMO-encoded-in-CGC-Item

ServingCellMO-encoded-in-CGC-Item ::= SEQUENCE {
	servingCellMO					ServingCellMO,
	iE-Extensions					ProtocolExtensionContainer { { ServingCellMO-encoded-in-CGC-Item-ExtIEs } }	OPTIONAL,
	...
}

ServingCellMO-encoded-in-CGC-Item-ExtIEs	F1AP-PROTOCOL-EXTENSION ::= {
	...
}

Served-Cell-Information ::= SEQUENCE {
	nRCGI							NRCGI,
	nRPCI							NRPCI,
	fiveGS-TAC						FiveGS-TAC			OPTIONAL,
	configured-EPS-TAC				Configured-EPS-TAC 		OPTIONAL,
	servedPLMNs						ServedPLMNs-List,
	nR-Mode-Info					NR-Mode-Info,
	measurementTimingConfiguration	OCTET STRING,
	iE-Extensions		ProtocolExtensionContainer { {Served-Cell-Information-ExtIEs} } OPTIONAL,
	...
}

Served-Cell-Information-ExtIEs F1AP-PROTOCOL-EXTENSION ::= {
	{	ID id-RANAC							CRITICALITY ignore	EXTENSION RANAC							PRESENCE optional }|
	{	ID id-ExtendedServedPLMNs-List		CRITICALITY ignore	EXTENSION ExtendedServedPLMNs-List	PRESENCE optional }|
	{	ID id-Cell-Direction				CRITICALITY ignore	EXTENSION Cell-Direction				PRESENCE optional }|
	{	ID id-BPLMN-ID-Info-List			CRITICALITY ignore	EXTENSION BPLMN-ID-Info-List			PRESENCE optional }|
	{	ID id-Cell-Type						CRITICALITY ignore	EXTENSION CellType						PRESENCE optional}|
	{	ID id-ConfiguredTACIndication		CRITICALITY ignore	EXTENSION ConfiguredTACIndication		PRESENCE optional }|
	{	ID id-AggressorgNBSetID				CRITICALITY ignore	EXTENSION AggressorgNBSetID				PRESENCE optional}|
	{	ID id-VictimgNBSetID				CRITICALITY ignore	EXTENSION VictimgNBSetID				PRESENCE optional}|
	{	ID id-IAB-Info-IAB-DU				CRITICALITY ignore	EXTENSION IAB-Info-IAB-DU				PRESENCE optional}|
	{	ID id-SSB-PositionsInBurst			CRITICALITY ignore	EXTENSION SSB-PositionsInBurst			PRESENCE optional }|
	{	ID id-NRPRACHConfig					CRITICALITY ignore	EXTENSION NRPRACHConfig					PRESENCE optional }|
	{	ID id-SFN-Offset					CRITICALITY ignore	EXTENSION SFN-Offset					PRESENCE optional }|
	{	ID id-NPNBroadcastInformation		CRITICALITY reject 	EXTENSION NPNBroadcastInformation		PRESENCE optional }|
	{	ID id-Supported-MBS-FSA-ID-List				CRITICALITY ignore	EXTENSION Supported-MBS-FSA-ID-List						PRESENCE optional }|
	{	ID id-Redcap-Bcast-Information		CRITICALITY ignore	EXTENSION Redcap-Bcast-Information	PRESENCE optional },
	...
}

Serving-Cells-List ::= SEQUENCE (SIZE(1..maxnoofServingCells)) OF Serving-Cells-List-Item

Serving-Cells-List-Item ::= SEQUENCE{
	nRCGI 								NRCGI,
	iAB-MT-Cell-NA-Resource-Configuration-Mode-Info       IAB-MT-Cell-NA-Resource-Configuration-Mode-Info		OPTIONAL,
	iE-Extensions			ProtocolExtensionContainer {{Serving-Cells-List-Item-ExtIEs}}		OPTIONAL
}

Serving-Cells-List-Item-ExtIEs 	F1AP-PROTOCOL-EXTENSION ::= {
	...
}

Supported-MBS-FSA-ID-List::= SEQUENCE (SIZE(1.. maxnoofMBSFSAs)) OF MBS-FrequencySelectionArea-Identity

MBS-FrequencySelectionArea-Identity::= OCTET STRING (SIZE(3))

SFN-Offset ::= SEQUENCE {
	sFN-Time-Offset					BIT STRING (SIZE(24)),
	iE-Extensions		ProtocolExtensionContainer { {SFN-Offset-ExtIEs} } OPTIONAL,
	...
}

SFN-Offset-ExtIEs F1AP-PROTOCOL-EXTENSION ::= {
		...
}

Served-Cells-To-Add-Item ::= SEQUENCE {
	served-Cell-Information		Served-Cell-Information,
	gNB-DU-System-Information	GNB-DU-System-Information	 OPTIONAL,
	iE-Extensions				ProtocolExtensionContainer { { Served-Cells-To-Add-ItemExtIEs} }	OPTIONAL,
	...
}

Served-Cells-To-Add-ItemExtIEs 	F1AP-PROTOCOL-EXTENSION ::= {
	...
}

Served-Cells-To-Delete-Item ::= SEQUENCE {
	oldNRCGI					NRCGI	,
	iE-Extensions				ProtocolExtensionContainer { { Served-Cells-To-Delete-ItemExtIEs } }	OPTIONAL,
	...
}

Served-Cells-To-Delete-ItemExtIEs 	F1AP-PROTOCOL-EXTENSION ::= {
	...
}

Served-Cells-To-Modify-Item ::= SEQUENCE {
	oldNRCGI					NRCGI							,
	served-Cell-Information		Served-Cell-Information		,
	gNB-DU-System-Information	GNB-DU-System-Information 	OPTIONAL	,
	iE-Extensions				ProtocolExtensionContainer { { Served-Cells-To-Modify-ItemExtIEs } }	OPTIONAL,
	...
}

Served-Cells-To-Modify-ItemExtIEs 	F1AP-PROTOCOL-EXTENSION ::= {
	...
}

Served-EUTRA-Cells-Information::= SEQUENCE {
	eUTRA-Mode-Info						EUTRA-Mode-Info,
	protectedEUTRAResourceIndication	ProtectedEUTRAResourceIndication,
	iE-Extensions						ProtocolExtensionContainer { {Served-EUTRA-Cell-Information-ExtIEs} } OPTIONAL,
	...
}

Served-EUTRA-Cell-Information-ExtIEs 	F1AP-PROTOCOL-EXTENSION ::= {
	...
}

Service-State ::= ENUMERATED {
	in-service,
	out-of-service,
	...
}

Service-Status ::= SEQUENCE {
	service-state				Service-State,
	switchingOffOngoing			ENUMERATED {true, ...}	OPTIONAL,
	iE-Extensions				ProtocolExtensionContainer { { Service-Status-ExtIEs } }	OPTIONAL,
	...
}

Service-Status-ExtIEs 	F1AP-PROTOCOL-EXTENSION ::= {
	...
}


RelativeTime1900 ::= 	BIT STRING (SIZE (64))

ShortDRXCycleLength ::=  ENUMERATED {ms2, ms3, ms4, ms5, ms6, ms7, ms8, ms10, ms14, ms16, ms20, ms30, ms32, ms35, ms40, ms64, ms80, ms128, ms160, ms256, ms320, ms512, ms640, ...}

ShortDRXCycleTimer ::= INTEGER (1..16)

SIB1-message ::= OCTET STRING

SIB10-message ::= OCTET STRING

SIB12-message ::= OCTET STRING

SIB13-message ::= OCTET STRING

SIB14-message ::= OCTET STRING

SIB15-message ::= OCTET STRING

SIB17-message ::= OCTET STRING

SIB20-message ::= OCTET STRING

SItype ::= INTEGER (1..32, ...)

SItype-List ::= SEQUENCE (SIZE(1.. maxnoofSITypes)) OF SItype-Item

SItype-Item ::= SEQUENCE {
	sItype		SItype	,
	iE-Extensions	ProtocolExtensionContainer { { SItype-ItemExtIEs } }	OPTIONAL
}

SItype-ItemExtIEs 	F1AP-PROTOCOL-EXTENSION ::= {
	...
}

SibtypetobeupdatedListItem ::= SEQUENCE {
	sIBtype 			INTEGER (2..32,...),
	sIBmessage			OCTET STRING,
	valueTag			INTEGER (0..31,...),
	iE-Extensions		ProtocolExtensionContainer { { SibtypetobeupdatedListItem-ExtIEs } }	OPTIONAL,
	...
}

SibtypetobeupdatedListItem-ExtIEs 	F1AP-PROTOCOL-EXTENSION ::= {
	{ID	id-areaScope	CRITICALITY ignore	EXTENSION	AreaScope	PRESENCE optional},
	...
}

SidelinkRelayConfiguration ::= SEQUENCE {
	gNB-DU-UE-F1APIDofRelayUE			GNB-DU-UE-F1AP-ID,
	remoteUELocalID						RemoteUELocalID,
	sidelinkConfigurationContainer		SidelinkConfigurationContainer		OPTIONAL,
	iE-Extensions						ProtocolExtensionContainer { { SidelinkRelayConfiguration-ExtIEs } }		OPTIONAL,
	...
}

SidelinkRelayConfiguration-ExtIEs	F1AP-PROTOCOL-EXTENSION ::= {
	...
}


SidelinkConfigurationContainer ::= OCTET STRING

SLDRBID ::= INTEGER (1..512, ...)

SLDRBInformation ::= SEQUENCE {
	sLDRB-QoS				PC5QoSParameters,
	flowsMappedToSLDRB-List	FlowsMappedToSLDRB-List,
	...
}

SLDRBs-FailedToBeModified-Item	::= SEQUENCE {
	sLDRBID		SLDRBID		,
	cause		Cause		OPTIONAL,
	iE-Extensions	ProtocolExtensionContainer { { SLDRBs-FailedToBeModified-ItemExtIEs } }	OPTIONAL
}

SLDRBs-FailedToBeModified-ItemExtIEs 	F1AP-PROTOCOL-EXTENSION ::= {
	...
}

SLDRBs-FailedToBeSetup-Item	::= SEQUENCE {
	sLDRBID	SLDRBID,
	cause	Cause	OPTIONAL,
	iE-Extensions	ProtocolExtensionContainer { { SLDRBs-FailedToBeSetup-ItemExtIEs } }		OPTIONAL
}

SLDRBs-FailedToBeSetup-ItemExtIEs 	F1AP-PROTOCOL-EXTENSION ::= {
	...
}

SLDRBs-FailedToBeSetupMod-Item	::= SEQUENCE {
	sLDRBID			SLDRBID	,
	cause			Cause			OPTIONAL ,
	iE-Extensions	ProtocolExtensionContainer { { SLDRBs-FailedToBeSetupMod-ItemExtIEs } }	OPTIONAL
}

SLDRBs-FailedToBeSetupMod-ItemExtIEs 	F1AP-PROTOCOL-EXTENSION ::= {
	...
}

SLDRBs-Modified-Item	::= SEQUENCE {
	sLDRBID							SLDRBID,
	iE-Extensions	ProtocolExtensionContainer { { SLDRBs-Modified-ItemExtIEs } }	OPTIONAL
}

SLDRBs-Modified-ItemExtIEs 	F1AP-PROTOCOL-EXTENSION ::= {
	...
}

SLDRBs-ModifiedConf-Item	::= SEQUENCE {
	sLDRBID							SLDRBID,
	iE-Extensions	ProtocolExtensionContainer { { SLDRBs-ModifiedConf-ItemExtIEs } }	OPTIONAL
}

SLDRBs-ModifiedConf-ItemExtIEs 	F1AP-PROTOCOL-EXTENSION ::= {
	...
}

SLDRBs-Required-ToBeModified-Item	::= SEQUENCE {
	sLDRBID							SLDRBID,
	iE-Extensions	ProtocolExtensionContainer { { SLDRBs-Required-ToBeModified-ItemExtIEs } }	OPTIONAL
}

SLDRBs-Required-ToBeModified-ItemExtIEs 	F1AP-PROTOCOL-EXTENSION ::= {
	...
}

SLDRBs-Required-ToBeReleased-Item	::= SEQUENCE {
	sLDRBID		SLDRBID,
	iE-Extensions	ProtocolExtensionContainer { { SLDRBs-Required-ToBeReleased-ItemExtIEs } }	OPTIONAL
}

SLDRBs-Required-ToBeReleased-ItemExtIEs 	F1AP-PROTOCOL-EXTENSION ::= {
	...
}

SLDRBs-Setup-Item ::= SEQUENCE {
	sLDRBID							SLDRBID,
	iE-Extensions	ProtocolExtensionContainer { { SLDRBs-Setup-ItemExtIEs } }	OPTIONAL
}

SLDRBs-Setup-ItemExtIEs 	F1AP-PROTOCOL-EXTENSION ::= {
	...
}

SLDRBs-SetupMod-Item	::= SEQUENCE {
	sLDRBID							SLDRBID,
	iE-Extensions	ProtocolExtensionContainer { { SLDRBs-SetupMod-ItemExtIEs } }	OPTIONAL
}

SLDRBs-SetupMod-ItemExtIEs 	F1AP-PROTOCOL-EXTENSION ::= {
	...
}

SLDRBs-ToBeModified-Item	::= SEQUENCE {
	sLDRBID						SLDRBID,
	sLDRBInformation			SLDRBInformation		OPTIONAL,
	rLCMode						RLCMode					OPTIONAL,
	iE-Extensions	ProtocolExtensionContainer { { SLDRBs-ToBeModified-ItemExtIEs } }	OPTIONAL
}

SLDRBs-ToBeModified-ItemExtIEs 	F1AP-PROTOCOL-EXTENSION ::= {
	...
}

SLDRBs-ToBeReleased-Item	::= SEQUENCE {
	sLDRBID			SLDRBID,
	iE-Extensions	ProtocolExtensionContainer { { SLDRBs-ToBeReleased-ItemExtIEs } }	OPTIONAL
}

SLDRBs-ToBeReleased-ItemExtIEs 	F1AP-PROTOCOL-EXTENSION ::= {
	...
}

SLDRBs-ToBeSetup-Item ::= SEQUENCE	{
	sLDRBID						SLDRBID,
	sLDRBInformation			SLDRBInformation,
	rLCMode						RLCMode,

	iE-Extensions	ProtocolExtensionContainer { { SLDRBs-ToBeSetup-ItemExtIEs } }	OPTIONAL
}

SLDRBs-ToBeSetup-ItemExtIEs 	F1AP-PROTOCOL-EXTENSION ::= {
	...
}

SLDRBs-ToBeSetupMod-Item	::= SEQUENCE {
	sLDRBID						SLDRBID,
	sLDRBInformation			SLDRBInformation,
	rLCMode						RLCMode			OPTIONAL,
	iE-Extensions	ProtocolExtensionContainer { { SLDRBs-ToBeSetupMod-ItemExtIEs } }	OPTIONAL
}

SLDRBs-ToBeSetupMod-ItemExtIEs 	F1AP-PROTOCOL-EXTENSION ::= {
	...
}

SLDRXCycleList ::= SEQUENCE (SIZE(1.. maxnoofSLdestinations)) OF SLDRXCycleItem
SLDRXCycleItem ::= SEQUENCE {
	rXUEID					BIT STRING (SIZE(24)),
	sLDRXInformation		SLDRXInformation,
	iE-Extensions			ProtocolExtensionContainer { { SLDRXCycleItem-ExtIEs } }	OPTIONAL,
	...
}

SLDRXCycleItem-ExtIEs	F1AP-PROTOCOL-EXTENSION ::= {
	...
}

SLDRXInformation    ::= CHOICE {
	sLDRXCycle			SLDRXCycleLength,
	nosLDRX				SLDRXConfigurationIndicator,
	choice-extension	ProtocolIE-SingleContainer { { SLDRXInformation-ExtIEs} }
}

SLDRXCycleLength ::= ENUMERATED{ms10, ms20, ms32, ms40, ms60, ms64, ms70, ms80, ms128, ms160, ms256, ms320, ms512, ms640, ms1024, ms1280, ms2048, ms2560, ms5120, ms10240, ...}

SLDRXConfigurationIndicator ::= ENUMERATED{ release, ...}


SLDRXInformation-ExtIEs F1AP-PROTOCOL-IES ::= {
	...
}

SL-PHY-MAC-RLC-Config ::= OCTET STRING

SL-RLC-ChannelToAddModList::= OCTET STRING

SL-ConfigDedicatedEUTRA-Info ::= OCTET STRING

SliceAvailableCapacity ::= SEQUENCE {
	sliceAvailableCapacityList	SliceAvailableCapacityList,
	iE-Extensions				ProtocolExtensionContainer { { SliceAvailableCapacity-ExtIEs} } OPTIONAL
}

SliceAvailableCapacity-ExtIEs 	F1AP-PROTOCOL-EXTENSION ::= {
	...
}

SliceAvailableCapacityList ::= SEQUENCE (SIZE(1.. maxnoofBPLMNsNR)) OF SliceAvailableCapacityItem

SliceAvailableCapacityItem ::= SEQUENCE {
	pLMNIdentity					PLMN-Identity,
	sNSSAIAvailableCapacity-List	SNSSAIAvailableCapacity-List,
	iE-Extensions	ProtocolExtensionContainer { { SliceAvailableCapacityItem-ExtIEs} } OPTIONAL
}

SliceAvailableCapacityItem-ExtIEs 	F1AP-PROTOCOL-EXTENSION ::= {
	...
}

SNSSAIAvailableCapacity-List ::= SEQUENCE (SIZE(1.. maxnoofSliceItems)) OF SNSSAIAvailableCapacity-Item

SNSSAIAvailableCapacity-Item ::= SEQUENCE {
	sNSSAI		SNSSAI,
	sliceAvailableCapacityValueDownlink	INTEGER (0..100)	OPTIONAL,
	sliceAvailableCapacityValueUplink	INTEGER (0..100)	OPTIONAL,
	iE-Extensions				ProtocolExtensionContainer { { SNSSAIAvailableCapacity-Item-ExtIEs } }	OPTIONAL
}

SNSSAIAvailableCapacity-Item-ExtIEs	F1AP-PROTOCOL-EXTENSION ::= {
	...
}

SliceRadioResourceStatus ::= SEQUENCE {
	sliceRadioResourceStatus	SliceRadioResourceStatus-List,
	iE-Extensions				ProtocolExtensionContainer { { SliceRadioResourceStatus-ExtIEs} } OPTIONAL
}

SliceRadioResourceStatus-ExtIEs 	F1AP-PROTOCOL-EXTENSION ::= {
	...
}


SliceRadioResourceStatus-List ::= SEQUENCE (SIZE(1..maxnoofBPLMNsNR)) OF SliceRadioResourceStatus-Item

SliceRadioResourceStatus-Item::= SEQUENCE {
	pLMNIdentity					PLMN-Identity,
	sNSSAIRadioResourceStatus-List	SNSSAIRadioResourceStatus-List,
	iE-Extensions					ProtocolExtensionContainer { { SliceRadioResourceStatus-Item-ExtIEs} } OPTIONAL
}

SliceRadioResourceStatus-Item-ExtIEs 	F1AP-PROTOCOL-EXTENSION ::= {
	...
}

SNSSAIRadioResourceStatus-List ::= SEQUENCE (SIZE(1.. maxnoofSliceItems)) OF SNSSAIRadioResourceStatus-Item

SNSSAIRadioResourceStatus-Item ::= SEQUENCE {
	sNSSAI		SNSSAI,
	sNSSAIdlGBRPRBusage			INTEGER (0..100),
	sNSSAIulGBRPRBusage			INTEGER (0..100),
	sNSSAIdlNonGBRPRBusage		INTEGER (0..100),
	sNSSAIulNonGBRPRBusage		INTEGER (0..100),
	sNSSAIdlTotalPRBallocation	INTEGER (0..100),
	sNSSAIulTotalPRBallocation	INTEGER (0..100),
	iE-Extensions				ProtocolExtensionContainer { { SNSSAIRadioResourceStatus-Item-ExtIEs } }	OPTIONAL
}

SNSSAIRadioResourceStatus-Item-ExtIEs	F1AP-PROTOCOL-EXTENSION ::= {
	...
}

SliceSupportList ::= SEQUENCE (SIZE(1.. maxnoofSliceItems)) OF SliceSupportItem

SliceSupportItem ::= SEQUENCE {
	sNSSAI	SNSSAI,
	iE-Extensions				ProtocolExtensionContainer { { SliceSupportItem-ExtIEs } }	OPTIONAL
}

SliceSupportItem-ExtIEs	F1AP-PROTOCOL-EXTENSION ::= {
	...
}

SliceToReportList ::= SEQUENCE (SIZE(1.. maxnoofBPLMNsNR)) OF SliceToReportItem

SliceToReportItem ::= SEQUENCE {
	pLMNIdentity				PLMN-Identity,
	sNSSAIlist					SNSSAI-list,
	iE-Extensions				ProtocolExtensionContainer { { SliceToReportItem-ExtIEs} } OPTIONAL
}

SliceToReportItem-ExtIEs 	F1AP-PROTOCOL-EXTENSION ::= {
	...
}

SlotNumber ::= INTEGER (0..79)

SNSSAI-list ::= SEQUENCE (SIZE(1.. maxnoofSliceItems)) OF SNSSAI-Item

SNSSAI-Item ::= SEQUENCE {
	sNSSAI		SNSSAI,
	iE-Extensions				ProtocolExtensionContainer { { SNSSAI-Item-ExtIEs } }	OPTIONAL
}

SNSSAI-Item-ExtIEs	F1AP-PROTOCOL-EXTENSION ::= {
	...
}

Slot-Configuration-List ::= SEQUENCE (SIZE(1.. maxnoofslots)) OF Slot-Configuration-Item

Slot-Configuration-Item ::= SEQUENCE {
	slotIndex				INTEGER (0..5119, ...),
	symbolAllocInSlot		SymbolAllocInSlot,
	iE-Extensions			ProtocolExtensionContainer { { Slot-Configuration-ItemExtIEs } }	OPTIONAL
}

Slot-Configuration-ItemExtIEs	F1AP-PROTOCOL-EXTENSION ::= {
	...
}


SNSSAI ::= SEQUENCE {
	sST			OCTET STRING (SIZE(1)),
	sD			OCTET STRING (SIZE(3)) 	OPTIONAL	,
	iE-Extensions				ProtocolExtensionContainer { { SNSSAI-ExtIEs } }	OPTIONAL
}

SNSSAI-ExtIEs	F1AP-PROTOCOL-EXTENSION ::= {
	...
}

SpatialDirectionInformation ::= SEQUENCE {
	nR-PRSBeamInformation			NR-PRSBeamInformation,
	iE-Extensions					ProtocolExtensionContainer { { SpatialDirectionInformation-ExtIEs } } OPTIONAL
}

SpatialDirectionInformation-ExtIEs F1AP-PROTOCOL-EXTENSION ::= {
	...
}

SpatialRelationInfo ::= SEQUENCE {
	spatialRelationforResourceID					SpatialRelationforResourceID,
	iE-Extensions		ProtocolExtensionContainer { {SpatialRelationInfo-ExtIEs} }	OPTIONAL
}

SpatialRelationInfo-ExtIEs F1AP-PROTOCOL-EXTENSION ::= {
	...
}

SpatialRelationforResourceID ::= SEQUENCE (SIZE(1..maxnoofSpatialRelations)) OF SpatialRelationforResourceIDItem

SpatialRelationforResourceIDItem ::= SEQUENCE {
	referenceSignal		ReferenceSignal,
	iE-Extensions		ProtocolExtensionContainer { {SpatialRelationforResourceIDItem-ExtIEs} }	OPTIONAL
}

SpatialRelationforResourceIDItem-ExtIEs F1AP-PROTOCOL-EXTENSION ::= {
	...
}

SpatialRelationPerSRSResource ::= SEQUENCE {
	spatialRelationPerSRSResource-List	SpatialRelationPerSRSResource-List,
	iE-Extensions		ProtocolExtensionContainer { { SpatialRelationPerSRSResource-ExtIEs} }	OPTIONAL,
	...
}

SpatialRelationPerSRSResource-ExtIEs F1AP-PROTOCOL-EXTENSION ::= {
	...
}

SpatialRelationPerSRSResource-List::= SEQUENCE(SIZE (1.. maxnoSRS-ResourcePerSet)) OF SpatialRelationPerSRSResourceItem

SpatialRelationPerSRSResourceItem ::= SEQUENCE {
	referenceSignal		ReferenceSignal,
	iE-Extensions		ProtocolExtensionContainer { { SpatialRelationPerSRSResourceItem-ExtIEs} }	OPTIONAL,
	...
}

SpatialRelationPerSRSResourceItem-ExtIEs F1AP-PROTOCOL-EXTENSION ::= {
	...
}

SpatialRelationPos ::= CHOICE {
	sSBPos					SSB,
	pRSInformationPos		PRSInformationPos,
	choice-extension		ProtocolIE-SingleContainer {{ SpatialInformationPos-ExtIEs }}
}

SpatialInformationPos-ExtIEs F1AP-PROTOCOL-IES ::= {
	...
}

SpectrumSharingGroupID ::= INTEGER (1..maxCellineNB)

SRBID ::= INTEGER (0..3, ...)

SRBs-FailedToBeSetup-Item	::= SEQUENCE {
	sRBID		SRBID	,
	cause		Cause	OPTIONAL,
	iE-Extensions	ProtocolExtensionContainer { { SRBs-FailedToBeSetup-ItemExtIEs } }	OPTIONAL,
	...
}

SRBs-FailedToBeSetup-ItemExtIEs 	F1AP-PROTOCOL-EXTENSION ::= {
	...
}

SRBs-FailedToBeSetupMod-Item	::= SEQUENCE {
	sRBID		SRBID		,
	cause		Cause		OPTIONAL,
	iE-Extensions	ProtocolExtensionContainer { { SRBs-FailedToBeSetupMod-ItemExtIEs } }	OPTIONAL,
	...
}

SRBs-FailedToBeSetupMod-ItemExtIEs 	F1AP-PROTOCOL-EXTENSION ::= {
	...
}

SRBs-Modified-Item ::= SEQUENCE {
	sRBID							SRBID,
	lCID							LCID,
	iE-Extensions	ProtocolExtensionContainer { { SRBs-Modified-ItemExtIEs } }	OPTIONAL,
	...
}

SRBs-Modified-ItemExtIEs	F1AP-PROTOCOL-EXTENSION ::= {
	...
}

SRBs-Required-ToBeReleased-Item	::= SEQUENCE {
	sRBID	SRBID,
	iE-Extensions	ProtocolExtensionContainer { { SRBs-Required-ToBeReleased-ItemExtIEs } }	OPTIONAL,
	...
}

SRBs-Required-ToBeReleased-ItemExtIEs 	F1AP-PROTOCOL-EXTENSION ::= {
	...
}

SRBs-Setup-Item ::= SEQUENCE {
	sRBID							SRBID,
	lCID								LCID,
	iE-Extensions	ProtocolExtensionContainer { { SRBs-Setup-ItemExtIEs } }	OPTIONAL,
	...
}

SRBs-Setup-ItemExtIEs 	F1AP-PROTOCOL-EXTENSION ::= {
	...
}

SRBs-SetupMod-Item ::= SEQUENCE {
	sRBID						SRBID,
	lCID							LCID,
	iE-Extensions	ProtocolExtensionContainer { { SRBs-SetupMod-ItemExtIEs } }	OPTIONAL,
	...
}

SRBs-SetupMod-ItemExtIEs 	F1AP-PROTOCOL-EXTENSION ::= {
	...
}

SRBs-ToBeReleased-Item	::= SEQUENCE {
	sRBID		SRBID,
	iE-Extensions	ProtocolExtensionContainer { { SRBs-ToBeReleased-ItemExtIEs } }	OPTIONAL,
	...
}

SRBs-ToBeReleased-ItemExtIEs 	F1AP-PROTOCOL-EXTENSION ::= {
	...
}

SRBs-ToBeSetup-Item ::= SEQUENCE {
	sRBID	 SRBID	,
	duplicationIndication	DuplicationIndication	OPTIONAL,
	iE-Extensions	ProtocolExtensionContainer { { SRBs-ToBeSetup-ItemExtIEs } }	OPTIONAL,
	...
}

SRBs-ToBeSetup-ItemExtIEs 	F1AP-PROTOCOL-EXTENSION ::= {
	{ ID id-AdditionalDuplicationIndication	CRITICALITY ignore	EXTENSION AdditionalDuplicationIndication		PRESENCE optional	}|
	{ ID id-SDTRLCBearerConfiguration		CRITICALITY ignore	EXTENSION SDTRLCBearerConfiguration				PRESENCE optional }|
	{ ID id-SRBMappingInfo					CRITICALITY ignore	EXTENSION UuRLCChannelID							PRESENCE optional	},
	...
}

SRBs-ToBeSetupMod-Item	::= SEQUENCE {
	sRBID	SRBID,
	duplicationIndication	DuplicationIndication	OPTIONAL,
	iE-Extensions	ProtocolExtensionContainer { { SRBs-ToBeSetupMod-ItemExtIEs } }	OPTIONAL,
	...
}

SRBs-ToBeSetupMod-ItemExtIEs 	F1AP-PROTOCOL-EXTENSION ::= {
	{ ID id-AdditionalDuplicationIndication	CRITICALITY ignore	EXTENSION AdditionalDuplicationIndication		PRESENCE optional	}|
	{ ID id-SRBMappingInfo					CRITICALITY ignore	EXTENSION UuRLCChannelID							PRESENCE optional	}|
	{ ID id-CG-SDTindicatorSetup			CRITICALITY reject	EXTENSION CG-SDTindicatorSetup						PRESENCE optional },
	...
}

SRSCarrier-List ::= SEQUENCE (SIZE(1.. maxnoSRS-Carriers)) OF SRSCarrier-List-Item

SRSCarrier-List-Item ::= SEQUENCE {
	pointA							INTEGER (0..3279165),
	uplinkChannelBW-PerSCS-List		UplinkChannelBW-PerSCS-List,
	activeULBWP						ActiveULBWP,
	pci								NRPCI		OPTIONAL,
	iE-Extensions					ProtocolExtensionContainer { { SRSCarrier-List-Item-ExtIEs } } OPTIONAL
}

SRSCarrier-List-Item-ExtIEs F1AP-PROTOCOL-EXTENSION ::= {
	...
}

SRSConfig  ::= SEQUENCE {
	sRSResource-List			SRSResource-List 		OPTIONAL,
	posSRSResource-List			PosSRSResource-List 	OPTIONAL,
	sRSResourceSet-List			SRSResourceSet-List 	OPTIONAL,
	posSRSResourceSet-List		PosSRSResourceSet-List 	OPTIONAL,
	iE-Extensions				ProtocolExtensionContainer { { SRSConfig-ExtIEs } } OPTIONAL
}

SRSConfig-ExtIEs F1AP-PROTOCOL-EXTENSION ::= {
	...
}

SRSConfiguration ::= SEQUENCE {
	sRSCarrier-List		SRSCarrier-List,
	iE-Extensions		ProtocolExtensionContainer { { SRSConfiguration-ExtIEs } } OPTIONAL
}

SRSConfiguration-ExtIEs F1AP-PROTOCOL-EXTENSION ::= {
	...
}

SrsFrequency ::= INTEGER (0..3279165)

SRSPortIndex ::= ENUMERATED {id1000, id1001, id1002, id1003,...}

SRSPosResourceID ::= INTEGER (0..63)

SRSResource::= SEQUENCE {
	sRSResourceID					SRSResourceID,
	nrofSRS-Ports					ENUMERATED {port1, ports2, ports4},
	transmissionComb				TransmissionComb,
	startPosition					INTEGER (0..13),
	nrofSymbols						ENUMERATED {n1, n2, n4},
	repetitionFactor				ENUMERATED {n1, n2, n4},
	freqDomainPosition				INTEGER (0..67),
	freqDomainShift					INTEGER (0..268),
	c-SRS							INTEGER (0..63),
	b-SRS							INTEGER (0..3),
	b-hop							INTEGER (0..3),
	groupOrSequenceHopping			ENUMERATED { neither, groupHopping, sequenceHopping },
	resourceType					ResourceType,
	sequenceId						INTEGER (0..1023),
	iE-Extensions					ProtocolExtensionContainer { { SRSResource-ExtIEs } } OPTIONAL
}

SRSResource-ExtIEs F1AP-PROTOCOL-EXTENSION ::= {
	...
}

SRSResourceID ::= INTEGER (0..63)

SRSResourceID-List::= SEQUENCE (SIZE (1..maxnoSRS-ResourcePerSet)) OF SRSResourceID

SRSResource-List ::= SEQUENCE (SIZE (1..maxnoSRS-Resources)) OF SRSResource

SRSResourceSet::= SEQUENCE {
	sRSResourceSetID				SRSResourceSetID,
	sRSResourceID-List				SRSResourceID-List,
	resourceSetType					ResourceSetType,
	iE-Extensions					ProtocolExtensionContainer { { SRSResourceSet-ExtIEs } } OPTIONAL
}

SRSResourceSet-ExtIEs F1AP-PROTOCOL-EXTENSION ::= {
	...
}

SRSResourceSetID ::= INTEGER (0..15, ...)

SRSResourceSetList ::= SEQUENCE (SIZE(1.. maxnoSRS-ResourceSets)) OF SRSResourceSetItem

SRSResourceSetItem ::= SEQUENCE {
	numSRSresourcesperset		INTEGER (1..16, ...)	OPTIONAL,
	periodicityList				PeriodicityList			OPTIONAL,
	spatialRelationInfo			SpatialRelationInfo		OPTIONAL,
	pathlossReferenceInfo		PathlossReferenceInfo	OPTIONAL,
	iE-Extensions	ProtocolExtensionContainer { { SRSResourceSetItemExtIEs } }	OPTIONAL
}

SRSResourceSetItemExtIEs	F1AP-PROTOCOL-EXTENSION ::= {
	{ ID id-SRSSpatialRelationPerSRSResource	CRITICALITY ignore	EXTENSION SpatialRelationPerSRSResource PRESENCE optional},
	...
}

SRSResourceSet-List ::= SEQUENCE (SIZE (1..maxnoSRS-ResourceSets)) OF SRSResourceSet

SRSResourceTrigger ::= SEQUENCE {
	aperiodicSRSResourceTriggerList					AperiodicSRSResourceTriggerList,
	iE-Extensions		ProtocolExtensionContainer { {SRSResourceTrigger-ExtIEs} }	OPTIONAL
}

SRSResourceTrigger-ExtIEs F1AP-PROTOCOL-EXTENSION ::= {
	...
}


SRSResourcetype ::= SEQUENCE {
	sRSResourceTypeChoice					SRSResourceTypeChoice,
	iE-Extensions		ProtocolExtensionContainer { { SRSResourcetype-ExtIEs} }	OPTIONAL,
	...
}

SRSResourcetype-ExtIEs F1AP-PROTOCOL-EXTENSION ::= {
	{ ID id-SRSPortIndex			CRITICALITY ignore EXTENSION SRSPortIndex	PRESENCE optional },
	...
}

SRSResourceTypeChoice ::= CHOICE {
	sRSResourceInfo				SRSInfo,
	posSRSResourceInfo			PosSRSInfo,
	choice-extension			ProtocolIE-SingleContainer { { SRSResourceTypeChoice-ExtIEs} }
}

SRSResourceTypeChoice-ExtIEs F1AP-PROTOCOL-IES ::= {
	...
}

SRSInfo ::= SEQUENCE {
	sRSResource			SRSResourceID,
	...
}

SRSPosRRCInactiveConfig ::= OCTET STRING

SRSPosRRCInactiveQueryIndication ::= ENUMERATED {true, ...}

PosSRSInfo ::= SEQUENCE {
	posSRSResourceID		SRSPosResourceID,
	...
}

SSB ::= SEQUENCE {
	pCI-NR				NRPCI,
	ssb-index			SSB-Index	OPTIONAL,
	iE-Extensions		ProtocolExtensionContainer { {SSB-ExtIEs} }	OPTIONAL
}

SSBCoverageModification-List ::= SEQUENCE (SIZE (1..maxnoofSSBAreas)) OF SSBCoverageModification-Item

SSBCoverageModification-Item::= SEQUENCE {
	sSBIndex						INTEGER(0..63),
	sSBCoverageState				SSBCoverageState,
	iE-Extensions		ProtocolExtensionContainer { { SSBCoverageModification-Item-ExtIEs} }	OPTIONAL,
...
}

SSBCoverageModification-Item-ExtIEs F1AP-PROTOCOL-EXTENSION ::= {
	...
}


SSBCoverageState ::= INTEGER (0..15, ...)


SSB-ExtIEs F1AP-PROTOCOL-EXTENSION ::= {
	...
}

SSB-freqInfo ::= INTEGER (0..maxNRARFCN)

SSB-Index ::= INTEGER(0..63)

SSB-subcarrierSpacing ::=  ENUMERATED {kHz15, kHz30, kHz120, kHz240, spare3, spare2, spare1, ...}

SSB-transmissionPeriodicity	::= ENUMERATED {sf10, sf20, sf40, sf80, sf160, sf320, sf640, ...}

SSB-transmissionTimingOffset ::= INTEGER (0..127, ...)

SSB-transmissionBitmap ::= CHOICE {
	shortBitmap			BIT STRING (SIZE (4)),
	mediumBitmap		BIT STRING (SIZE (8)),
	longBitmap			BIT STRING (SIZE (64)),
	choice-extension	ProtocolIE-SingleContainer { { SSB-transmisisonBitmap-ExtIEs} }
}

SSB-transmisisonBitmap-ExtIEs F1AP-PROTOCOL-IES ::= {
	...
}

SSBAreaCapacityValueList ::= SEQUENCE (SIZE(1.. maxnoofSSBAreas)) OF	SSBAreaCapacityValueItem

SSBAreaCapacityValueItem ::= SEQUENCE {
	sSBIndex				INTEGER(0..63),
	sSBAreaCapacityValue	INTEGER (0..100),
	iE-Extensions			ProtocolExtensionContainer { { SSBAreaCapacityValueItem-ExtIEs} } OPTIONAL
}

SSBAreaCapacityValueItem-ExtIEs 	F1AP-PROTOCOL-EXTENSION ::= {
	...
}

SSBAreaRadioResourceStatusList::= SEQUENCE (SIZE(1.. maxnoofSSBAreas)) OF	SSBAreaRadioResourceStatusItem

SSBAreaRadioResourceStatusItem::= SEQUENCE {
	sSBIndex					INTEGER(0..63),
	sSBAreaDLGBRPRBusage		INTEGER (0..100),
	sSBAreaULGBRPRBusage		INTEGER (0..100),
	sSBAreaDLnon-GBRPRBusage	INTEGER (0..100),
	sSBAreaULnon-GBRPRBusage	INTEGER (0..100),
	sSBAreaDLTotalPRBusage		INTEGER (0..100),
	sSBAreaULTotalPRBusage		INTEGER (0..100),
	dLschedulingPDCCHCCEusage	INTEGER (0..100)		OPTIONAL,
	uLschedulingPDCCHCCEusage	INTEGER (0..100) 		OPTIONAL,
	iE-Extensions				ProtocolExtensionContainer { { SSBAreaRadioResourceStatusItem-ExtIEs} } OPTIONAL
}

SSBAreaRadioResourceStatusItem-ExtIEs 	F1AP-PROTOCOL-EXTENSION ::= {
	...
}

SSBInformation ::= SEQUENCE {
	sSBInformationList	SSBInformationList,
	iE-Extensions		ProtocolExtensionContainer { { SSBInformation-ExtIEs } }	OPTIONAL
}

SSBInformation-ExtIEs 	F1AP-PROTOCOL-EXTENSION ::= {
	...
}

SSBInformationList ::= SEQUENCE (SIZE(1.. maxnoofSSBs)) OF SSBInformationItem

SSBInformationItem ::= SEQUENCE {
	sSB-Configuration	SSB-TF-Configuration,
	pCI-NR				NRPCI,
	iE-Extensions		ProtocolExtensionContainer { { SSBInformationItem-ExtIEs } }	OPTIONAL
}

SSBInformationItem-ExtIEs 	F1AP-PROTOCOL-EXTENSION ::= {
	...
}

SSB-PositionsInBurst ::= CHOICE {
	shortBitmap						BIT STRING (SIZE (4)),
	mediumBitmap					BIT STRING (SIZE (8)),
	longBitmap						BIT STRING (SIZE (64)),
	choice-extension				ProtocolIE-SingleContainer { {SSB-PositionsInBurst-ExtIEs} }
}

SSB-PositionsInBurst-ExtIEs F1AP-PROTOCOL-IES ::= {
	...
}

SSB-TF-Configuration ::= SEQUENCE {
	sSB-frequency				INTEGER (0..3279165),
	sSB-subcarrier-spacing		ENUMERATED {kHz15, kHz30, kHz60, kHz120, kHz240, ...},
	sSB-Transmit-power			INTEGER (-60..50),
	sSB-periodicity				ENUMERATED {ms5, ms10, ms20, ms40, ms80, ms160, ...},
	sSB-half-frame-offset		INTEGER(0..1),
	sSB-SFN-offset				INTEGER(0..15),
	sSB-position-in-burst		SSB-PositionsInBurst		OPTIONAL,
	sFNInitialisationTime		RelativeTime1900		OPTIONAL,
	iE-Extensions				ProtocolExtensionContainer { { SSB-TF-Configuration-ExtIEs} } OPTIONAL
}

SSB-TF-Configuration-ExtIEs 	F1AP-PROTOCOL-EXTENSION ::= {
	...
}


SSBToReportList ::= SEQUENCE (SIZE(1.. maxnoofSSBAreas)) OF SSBToReportItem

SSBToReportItem ::= SEQUENCE {
	sSBIndex					INTEGER(0..63),
	iE-Extensions				ProtocolExtensionContainer { { SSBToReportItem-ExtIEs} } OPTIONAL
}

SSBToReportItem-ExtIEs 	F1AP-PROTOCOL-EXTENSION ::= {
	...
}

StartTimeAndDuration ::= SEQUENCE {
	startTime			RelativeTime1900				OPTIONAL,
	duration			INTEGER (0..90060, ...)			OPTIONAL,
	iE-Extensions		ProtocolExtensionContainer { { StartTimeAndDuration-ExtIEs } }	OPTIONAL,
	...
}

StartTimeAndDuration-ExtIEs F1AP-PROTOCOL-EXTENSION ::= {
	...
}

SUL-Information ::= SEQUENCE {
	sUL-NRARFCN							INTEGER (0..maxNRARFCN),
	sUL-transmission-Bandwidth			Transmission-Bandwidth,
	iE-Extensions						ProtocolExtensionContainer { { SUL-InformationExtIEs} } OPTIONAL,
	...
}

SUL-InformationExtIEs 	F1AP-PROTOCOL-EXTENSION ::= {
	{ ID id-CarrierList				CRITICALITY ignore	EXTENSION NRCarrierList			PRESENCE optional }|
	{ ID id-FrequencyShift7p5khz	CRITICALITY ignore	EXTENSION FrequencyShift7p5khz	PRESENCE optional },
	...
}

SubcarrierSpacing ::=	ENUMERATED { kHz15, kHz30, kHz60, kHz120, kHz240, spare3, spare2, spare1, ...}

SubscriberProfileIDforRFP ::= INTEGER (1..256, ...)

SuccessfulHOReportInformationList::= SEQUENCE (SIZE(1.. maxnoofSuccessfulHOReports)) OF SuccessfulHOReportInformation-Item

SuccessfulHOReportInformation-Item ::= SEQUENCE {
	successfulHOReportContainer				OCTET STRING,
	iE-Extensions	ProtocolExtensionContainer { { SuccessfulHOReportInformation-Item-ExtIEs } }	OPTIONAL
}

SuccessfulHOReportInformation-Item-ExtIEs	F1AP-PROTOCOL-EXTENSION ::= {
	...
}

SULAccessIndication ::= ENUMERATED {true,...}


SupportedSULFreqBandItem ::= SEQUENCE {
	freqBandIndicatorNr 			INTEGER (1..1024,...),
	iE-Extensions					ProtocolExtensionContainer { { SupportedSULFreqBandItem-ExtIEs} } OPTIONAL,
	...
}

SupportedSULFreqBandItem-ExtIEs F1AP-PROTOCOL-EXTENSION ::= {
	...
}

SurvivalTime ::= INTEGER (0.. 1920000,...)

SymbolAllocInSlot ::= CHOICE {
	all-DL					NULL,
	all-UL					NULL,
	both-DL-and-UL			NumDLULSymbols,
	choice-extension		ProtocolIE-SingleContainer { { SymbolAllocInSlot-ExtIEs } }
}

SymbolAllocInSlot-ExtIEs F1AP-PROTOCOL-IES ::= {
	...
}

SystemFrameNumber ::= INTEGER (0..1023)

SystemInformationAreaID ::=BIT STRING (SIZE (24))

-- T

FiveGS-TAC ::= OCTET STRING (SIZE(3))

Configured-EPS-TAC ::= OCTET STRING (SIZE(2))

TargetCellList ::= SEQUENCE (SIZE(1..maxnoofCHOcells)) OF TargetCellList-Item

TargetCellList-Item ::= SEQUENCE {
	target-cell								NRCGI,
	iE-Extensions							ProtocolExtensionContainer { { TargetCellList-Item-ExtIEs} } OPTIONAL
}

TargetCellList-Item-ExtIEs F1AP-PROTOCOL-EXTENSION ::= {
	...
}

NSAGSupportList ::= SEQUENCE (SIZE(1.. maxnoofNSAGs)) OF NSAGSupportItem

NSAGSupportItem ::= SEQUENCE {
	nSAG-ID					NSAG-ID,
	nSAGSliceSupport		ExtendedSliceSupportList,
	iE-Extensions			ProtocolExtensionContainer { {NSAGSupportItem-ExtIEs} }	OPTIONAL,
	...
}

NSAGSupportItem-ExtIEs F1AP-PROTOCOL-EXTENSION ::= {
	...
}

NSAG-ID ::= INTEGER (0..255, ...)

TDD-Info ::= SEQUENCE {
	nRFreqInfo						NRFreqInfo,
	transmission-Bandwidth			Transmission-Bandwidth,
	iE-Extensions					ProtocolExtensionContainer { {TDD-Info-ExtIEs} } OPTIONAL,
	...
}

TDD-Info-ExtIEs F1AP-PROTOCOL-EXTENSION ::= {
	{ID	id-IntendedTDD-DL-ULConfig	CRITICALITY ignore	EXTENSION	IntendedTDD-DL-ULConfig	PRESENCE optional}|
	{ID id-TDD-UL-DLConfigCommonNR	CRITICALITY ignore	EXTENSION TDD-UL-DLConfigCommonNR	PRESENCE optional }|
	{ID id-CarrierList				CRITICALITY ignore	EXTENSION NRCarrierList				PRESENCE optional },
	...
}

TDD-InfoRel16 ::= SEQUENCE {
	tDD-FreqInfo									FreqInfoRel16													OPTIONAL,
	sUL-FreqInfo									FreqInfoRel16													OPTIONAL,
	tDD-UL-DLConfigCommonNR							TDD-UL-DLConfigCommonNR											OPTIONAL,
	iE-Extensions									ProtocolExtensionContainer { {TDD-InfoRel16-ExtIEs} }		OPTIONAL,
	...
}

TDD-InfoRel16-ExtIEs F1AP-PROTOCOL-EXTENSION ::= {
	...
}


TDD-UL-DLConfigCommonNR ::= OCTET STRING

TRPTEGInformation ::= CHOICE {
	rxTx-TEG			RxTxTEG,
	rx-TEG				RxTEG,
	choice-extension		ProtocolIE-SingleContainer { { TRPTEGInformation-ExtIEs} }
}

TRPTEGInformation-ExtIEs F1AP-PROTOCOL-IES ::= {
	...
}

RxTxTEG ::= SEQUENCE {
	tRP-RxTx-TEGInformation			TRP-RxTx-TEGInformation,
	tRP-Tx-TEGInformation			TRP-Tx-TEGInformation		OPTIONAL,
	iE-Extensions		ProtocolExtensionContainer { { RxTxTEG-ExtIEs } }		OPTIONAL,
	...
}

RxTxTEG-ExtIEs	F1AP-PROTOCOL-EXTENSION ::= {
	...
}

RxTEG ::= SEQUENCE {
	tRP-Rx-TEGInformation		TRP-Rx-TEGInformation,
	tRP-Tx-TEGInformation		TRP-Tx-TEGInformation,
	iE-Extensions			ProtocolExtensionContainer { { RxTEG-ExtIEs } }		OPTIONAL,
	...
}

RxTEG-ExtIEs	F1AP-PROTOCOL-EXTENSION ::= {
	...
}

TimeReferenceInformation ::= SEQUENCE {
	referenceTime					ReferenceTime,
	referenceSFN					ReferenceSFN,
	uncertainty						Uncertainty,
	timeInformationType				TimeInformationType,
	iE-Extensions		ProtocolExtensionContainer { {TimeReferenceInformation-ExtIEs} }	OPTIONAL
}

TimeReferenceInformation-ExtIEs F1AP-PROTOCOL-EXTENSION ::= {
	...
}

TimeInformationType ::= ENUMERATED {localClock}

TimeStamp ::= SEQUENCE {
	systemFrameNumber		SystemFrameNumber,
	slotIndex				TimeStampSlotIndex,
	measurementTime			RelativeTime1900	OPTIONAL,
	iE-Extension			ProtocolExtensionContainer { { TimeStamp-ExtIEs} }	OPTIONAL
}

TimeStamp-ExtIEs F1AP-PROTOCOL-EXTENSION ::= {
	...
}

TimeStampSlotIndex ::= CHOICE {
	sCS-15			INTEGER(0..9),
	sCS-30			INTEGER(0..19),
	sCS-60			INTEGER(0..39),
	sCS-120			INTEGER(0..79),
	choice-extension		ProtocolIE-SingleContainer { { TimeStampSlotIndex-ExtIEs} }
}

TimeStampSlotIndex-ExtIEs F1AP-PROTOCOL-IES ::= {
	{ ID id-SCS-480		CRITICALITY reject	TYPE SCS-480 PRESENCE mandatory}|
	{ ID id-SCS-960		CRITICALITY reject	TYPE SCS-960 PRESENCE mandatory},
	...
}

TimeToWait ::= ENUMERATED {v1s, v2s, v5s, v10s, v20s, v60s, ...}

TimingErrorMargin ::= ENUMERATED {m0Tc, m2Tc, m4Tc, m6Tc, m8Tc, m12Tc, m16Tc, m20Tc, m24Tc, m32Tc, m40Tc, m48Tc, m56Tc, m64Tc, m72Tc, m80Tc, ...}

TimingMeasurementQuality ::= SEQUENCE {
	measurementQuality		INTEGER(0..31),
	resolution				ENUMERATED{m0dot1, m1, m10, m30, ...},
	iE-Extensions			ProtocolExtensionContainer { { TimingMeasurementQuality-ExtIEs} }	OPTIONAL
}

TimingMeasurementQuality-ExtIEs F1AP-PROTOCOL-EXTENSION ::= {
	...
}

TMGI ::=  OCTET STRING (SIZE(6))

TNLAssociationUsage ::= ENUMERATED {
	ue,
	non-ue,
	both,
	...
}

TNLCapacityIndicator::= SEQUENCE {
	dLTNLOfferedCapacity		INTEGER (1.. 16777216,...),
	dLTNLAvailableCapacity		INTEGER (0.. 100,...),
	uLTNLOfferedCapacity		INTEGER (1.. 16777216,...),
	uLTNLAvailableCapacity		INTEGER (0.. 100,...),
	iE-Extensions	ProtocolExtensionContainer { { TNLCapacityIndicator-ExtIEs} } OPTIONAL
}

TNLCapacityIndicator-ExtIEs 	F1AP-PROTOCOL-EXTENSION ::= {
	...
}

TraceActivation ::= SEQUENCE {
	traceID								TraceID,
	interfacesToTrace					InterfacesToTrace,
	traceDepth							TraceDepth,
	traceCollectionEntityIPAddress		TransportLayerAddress,
	iE-Extensions		ProtocolExtensionContainer { {TraceActivation-ExtIEs} }	OPTIONAL
}

TraceActivation-ExtIEs F1AP-PROTOCOL-EXTENSION ::= {
	{ID id-mdtConfiguration			CRITICALITY ignore	EXTENSION	MDTConfiguration		PRESENCE optional}|
	{ID id-TraceCollectionEntityURI	CRITICALITY ignore	EXTENSION URI-address				PRESENCE optional	},
	...
}

TraceDepth ::= ENUMERATED {
	minimum,
	medium,
	maximum,
	minimumWithoutVendorSpecificExtension,
	mediumWithoutVendorSpecificExtension,
	maximumWithoutVendorSpecificExtension,
	...
}

TraceID ::= OCTET STRING (SIZE(8))

TrafficMappingInfo	::= CHOICE {
	iPtolayer2TrafficMappingInfo					IPtolayer2TrafficMappingInfo,
	bAPlayerBHRLCchannelMappingInfo					BAPlayerBHRLCchannelMappingInfo,
	choice-extension								ProtocolIE-SingleContainer { { TrafficMappingInfo-ExtIEs} }
}

TrafficMappingInfo-ExtIEs F1AP-PROTOCOL-IES ::= {
	...
}

TransportLayerAddress		::= BIT STRING (SIZE(1..160, ...))

TransactionID				::= INTEGER (0..255, ...)

Transmission-Bandwidth ::= SEQUENCE {
	nRSCS	NRSCS,
	nRNRB	NRNRB,
	iE-Extensions				ProtocolExtensionContainer { { Transmission-Bandwidth-ExtIEs} } OPTIONAL,
	...
}

Transmission-Bandwidth-ExtIEs F1AP-PROTOCOL-EXTENSION ::= {
	...
}

TransmissionComb ::= CHOICE {
	n2    SEQUENCE {
            combOffset-n2              INTEGER (0..1),
            cyclicShift-n2             INTEGER (0..7)
        },
    n4    SEQUENCE {
            combOffset-n4              INTEGER (0..3),
            cyclicShift-n4             INTEGER (0..11)
        },
	choice-extension				ProtocolIE-SingleContainer { { TransmissionComb-ExtIEs} }
}
TransmissionComb-ExtIEs F1AP-PROTOCOL-IES ::= {
	...
}

TransmissionCombPos ::= CHOICE {
	n2    SEQUENCE {
            combOffset-n2              INTEGER (0..1),
            cyclicShift-n2             INTEGER (0..7)
        },
    n4    SEQUENCE {
            combOffset-n4              INTEGER (0..3),
            cyclicShift-n4             INTEGER (0..11)
        },
    n8    SEQUENCE {
            combOffset-n8              INTEGER (0..7),
            cyclicShift-n8             INTEGER (0..5)
        },

	choice-extension				ProtocolIE-SingleContainer { { TransmissionCombPos-ExtIEs} }
}
TransmissionCombPos-ExtIEs F1AP-PROTOCOL-IES ::= {
	...
}

TransmissionStopIndicator ::= ENUMERATED {true, ... }

Transport-UP-Layer-Address-Info-To-Add-List	::= SEQUENCE (SIZE(1.. maxnoofTLAs)) OF Transport-UP-Layer-Address-Info-To-Add-Item

Transport-UP-Layer-Address-Info-To-Add-Item ::= SEQUENCE {
	iP-SecTransportLayerAddress		TransportLayerAddress,
	gTPTransportLayerAddressToAdd			GTPTLAs							OPTIONAL,
	iE-Extensions					ProtocolExtensionContainer { { Transport-UP-Layer-Address-Info-To-Add-ItemExtIEs } }	OPTIONAL
}

Transport-UP-Layer-Address-Info-To-Add-ItemExtIEs F1AP-PROTOCOL-EXTENSION ::= {
	...
}

Transport-UP-Layer-Address-Info-To-Remove-List	::= SEQUENCE (SIZE(1.. maxnoofTLAs)) OF Transport-UP-Layer-Address-Info-To-Remove-Item

Transport-UP-Layer-Address-Info-To-Remove-Item ::= SEQUENCE {
	iP-SecTransportLayerAddress		TransportLayerAddress,
	gTPTransportLayerAddressToRemove			GTPTLAs							OPTIONAL,
	iE-Extensions					ProtocolExtensionContainer { { Transport-UP-Layer-Address-Info-To-Remove-ItemExtIEs } }	OPTIONAL
}

Transport-UP-Layer-Address-Info-To-Remove-ItemExtIEs F1AP-PROTOCOL-EXTENSION ::= {
	...
}

TransmissionActionIndicator ::= ENUMERATED {stop, ..., restart }

TRPBeamAntennaInformation ::= SEQUENCE {
	choice-TRP-Beam-Antenna-Info-Item		Choice-TRP-Beam-Antenna-Info-Item								,
	iE-Extensions			ProtocolExtensionContainer {{ TRPBeamAntennaInformation-ExtIEs}}				OPTIONAL,
	...
}

TRPBeamAntennaInformation-ExtIEs F1AP-PROTOCOL-EXTENSION ::= {
	...
}

Choice-TRP-Beam-Antenna-Info-Item ::= CHOICE {
	reference					TRPID,
	explicit					TRP-BeamAntennaExplicitInformation,
	noChange					NULL,
	choice-extension			ProtocolIE-SingleContainer { { Choice-TRP-Beam-Info-Item-ExtIEs } }
}

Choice-TRP-Beam-Info-Item-ExtIEs F1AP-PROTOCOL-IES ::= {
	...
}

TRP-BeamAntennaExplicitInformation ::= SEQUENCE {
	trp-BeamAntennaAngles					TRP-BeamAntennaAngles,
	lcs-to-gcs-translation	 				LCS-to-GCS-Translation										OPTIONAL,
	iE-Extensions			ProtocolExtensionContainer {{ TRP-BeamAntennaExplicitInformation-ExtIEs}}				OPTIONAL,
	...
}

TRP-BeamAntennaExplicitInformation-ExtIEs F1AP-PROTOCOL-EXTENSION ::= {
	...
}



TRP-BeamAntennaAngles ::= SEQUENCE (SIZE (1.. maxnoAzimuthAngles)) OF TRP-BeamAntennaAnglesList-Item

TRP-BeamAntennaAnglesList-Item ::= SEQUENCE {
	trp-azimuth-angle					INTEGER (0..359),
	trp-azimuth-angle-fine				INTEGER (0..9)	OPTIONAL,
	trp-elevation-angle-list			SEQUENCE (SIZE (1.. maxnoElevationAngles)) OF TRP-ElevationAngleList-Item,
	iE-Extensions			ProtocolExtensionContainer {{ TRP-BeamAntennaAnglesList-Item-ExtIEs}}			OPTIONAL,
	...
}

TRP-BeamAntennaAnglesList-Item-ExtIEs F1AP-PROTOCOL-EXTENSION ::= {
	...
}

TRP-ElevationAngleList-Item ::= SEQUENCE {
	trp-elevation-angle					INTEGER (0..180),
	trp-elevation-angle-fine			INTEGER (0..9)	OPTIONAL,
	trp-beam-power-list					SEQUENCE (SIZE (2..maxNumResourcesPerAngle)) OF TRP-Beam-Power-Item,
	iE-Extensions			ProtocolExtensionContainer {{ TRP-ElevationAngleList-Item-ExtIEs}}			OPTIONAL,
...
}
TRP-ElevationAngleList-Item-ExtIEs F1AP-PROTOCOL-EXTENSION ::= {
	...
}

TRP-Beam-Power-Item ::= SEQUENCE {
	pRSResourceSetID				PRS-Resource-Set-ID													OPTIONAL,
	pRSResourceID					PRS-Resource-ID,
	relativePower					INTEGER (0..30), --negative value
	relativePowerFine				INTEGER (0..9)			OPTIONAL,
	iE-Extensions			ProtocolExtensionContainer {{ TRP-Beam-Power-Item-ExtIEs}}					OPTIONAL,
	...
}

TRP-Beam-Power-Item-ExtIEs F1AP-PROTOCOL-EXTENSION ::= {
	...
}


TRPID ::= INTEGER (0.. maxnoofTRPs, ...)

TRPInformation ::= SEQUENCE {
	tRPID							TRPID,
	tRPInformationTypeResponseList	TRPInformationTypeResponseList,
	iE-Extensions					ProtocolExtensionContainer { { TRPInformation-ExtIEs } }		OPTIONAL
}

TRPInformation-ExtIEs F1AP-PROTOCOL-EXTENSION ::= {
	...
}

TRPInformationItem ::= SEQUENCE {
	tRPInformation					TRPInformation,
	iE-Extensions					ProtocolExtensionContainer { { TRPInformationItem-ExtIEs } }	OPTIONAL
}

TRPInformationItem-ExtIEs F1AP-PROTOCOL-EXTENSION ::= {
	...
}

TRPInformationTypeItem ::= ENUMERATED {
		nrPCI,
		nG-RAN-CGI,
		arfcn,
		pRSConfig,
		sSBConfig,
		sFNInitTime,
		spatialDirectInfo,
		geoCoord,
		...,
		trp-type,
		ondemandPRS,
		trpTxTeg,
		beam-antenna-info
}


TRPInformationTypeResponseList ::= SEQUENCE (SIZE(1.. maxnoofTRPInfoTypes)) OF TRPInformationTypeResponseItem

TRPInformationTypeResponseItem ::= CHOICE {
	pCI-NR								NRPCI,
	nG-RAN-CGI							NRCGI,
	nRARFCN								INTEGER (0..maxNRARFCN),
	pRSConfiguration					PRSConfiguration,
	sSBinformation						SSBInformation,
	sFNInitialisationTime				RelativeTime1900,
	spatialDirectionInformation			SpatialDirectionInformation,
	geographicalCoordinates				GeographicalCoordinates,
	choice-extension					ProtocolIE-SingleContainer { { TRPInformationTypeResponseItem-ExtIEs} }
}

TRPInformationTypeResponseItem-ExtIEs F1AP-PROTOCOL-IES ::= {
	{ ID id-TRPType						CRITICALITY reject		TYPE TRPType					PRESENCE mandatory }|
	{ ID id-OnDemandPRS	 				CRITICALITY reject		TYPE OnDemandPRS-Info			PRESENCE mandatory}|
	{ ID id-TRPTxTEGAssociation			CRITICALITY reject		TYPE TRPTxTEGAssociation		PRESENCE optional }|
	{ ID id-TRPBeamAntennaInformation	CRITICALITY reject		TYPE TRPBeamAntennaInformation	PRESENCE mandatory },
	...
}


TRPList ::= SEQUENCE (SIZE(1.. maxnoofTRPs)) OF TRPListItem

TRPListItem ::= SEQUENCE {
	tRPID							TRPID,
	iE-Extensions					ProtocolExtensionContainer { { TRPListItem-ExtIEs } }	OPTIONAL
}

TRPListItem-ExtIEs F1AP-PROTOCOL-EXTENSION ::= {
	...
}

TRPMeasurementQuality ::= SEQUENCE {
	tRPmeasurementQuality-Item 	TRPMeasurementQuality-Item,
	iE-Extensions				ProtocolExtensionContainer { {TRPMeasurementQuality-ExtIEs} } OPTIONAL
}

TRPMeasurementQuality-ExtIEs 	F1AP-PROTOCOL-EXTENSION ::= {
	...
}

TRPMeasurementQuality-Item ::= CHOICE {
	timingMeasurementQuality	TimingMeasurementQuality,
	angleMeasurementQuality		AngleMeasurementQuality,
	choice-extension			ProtocolIE-SingleContainer { { TRPMeasurementQuality-Item-ExtIEs } }
}

TRPMeasurementQuality-Item-ExtIEs F1AP-PROTOCOL-IES ::= {
	...
}

TRP-MeasurementRequestList ::= SEQUENCE (SIZE (1..maxNoOfMeasTRPs)) OF TRP-MeasurementRequestItem

TRP-MeasurementRequestItem ::= SEQUENCE {
	tRPID							TRPID,
	search-window-information		Search-window-information	OPTIONAL,
	iE-extensions		ProtocolExtensionContainer { { TRP-MeasurementRequestItem-ExtIEs } } OPTIONAL
}

TRP-MeasurementRequestItem-ExtIEs F1AP-PROTOCOL-EXTENSION ::= {
	{ ID id-NRCGI					CRITICALITY ignore EXTENSION NRCGI					PRESENCE optional }|
	{ ID id-AoA-SearchWindow		CRITICALITY ignore EXTENSION AoA-AssistanceInfo		PRESENCE optional }|
	{ ID id-NumberOfTRPRxTEG		CRITICALITY ignore EXTENSION NumberOfTRPRxTEG		PRESENCE optional }|
	{ ID id-NumberOfTRPRxTxTEG		CRITICALITY ignore EXTENSION NumberOfTRPRxTxTEG		PRESENCE optional },
	...
}

TRP-PRS-Info-List ::= SEQUENCE (SIZE(1.. maxnoofPRSTRPs)) OF TRP-PRS-Info-List-Item

TRP-PRS-Info-List-Item ::= SEQUENCE {
		tRP-ID				TRPID,
		nR-PCI				NRPCI,
		cGI-NR				NRCGI					OPTIONAL,
		pRSConfiguration							PRSConfiguration,
		iE-Extensions	ProtocolExtensionContainer { { TRP-PRS-Info-List-Item-ExtIEs} } OPTIONAL,
		...
}

TRP-PRS-Info-List-Item-ExtIEs F1AP-PROTOCOL-EXTENSION ::= {
	...
}


TRPPositionDefinitionType ::= CHOICE {
	direct		TRPPositionDirect,
	referenced	TRPPositionReferenced,
	choice-extension							ProtocolIE-SingleContainer { { TRPPositionDefinitionType-ExtIEs } }
}

TRPPositionDefinitionType-ExtIEs F1AP-PROTOCOL-IES ::= {
	...
}

TRPPositionDirect ::= SEQUENCE {
	accuracy	TRPPositionDirectAccuracy,
	iE-extensions		ProtocolExtensionContainer { { TRPPositionDirect-ExtIEs } }	OPTIONAL
}

TRPPositionDirect-ExtIEs F1AP-PROTOCOL-EXTENSION ::= {
	...
}

TRPPositionDirectAccuracy ::= CHOICE {
	tRPPosition				AccessPointPosition,
	tRPHAposition			NGRANHighAccuracyAccessPointPosition,
	choice-extension		ProtocolIE-SingleContainer { { TRPPositionDirectAccuracy-ExtIEs } }
}

TRPPositionDirectAccuracy-ExtIEs F1AP-PROTOCOL-IES ::= {
	...
}

TRPPositionReferenced ::= SEQUENCE {
	referencePoint					ReferencePoint,
	referencePointType				TRPReferencePointType,
	iE-extensions					ProtocolExtensionContainer { { TRPPositionReferenced-ExtIEs } } 	OPTIONAL
}

TRPPositionReferenced-ExtIEs F1AP-PROTOCOL-EXTENSION ::= {
	...
}

TRPReferencePointType ::= CHOICE {
	tRPPositionRelativeGeodetic			RelativeGeodeticLocation,
	tRPPositionRelativeCartesian		RelativeCartesianLocation,
	choice-extension					ProtocolIE-SingleContainer { { TRPReferencePointType-ExtIEs } }
}

TRPReferencePointType-ExtIEs F1AP-PROTOCOL-IES ::= {
	...
}

TRP-Rx-TEGInformation ::= SEQUENCE {
	tRP-Rx-TEGID					INTEGER (0..31),
	tRP-Rx-TimingErrorMargin		TimingErrorMargin,
	iE-Extensions		ProtocolExtensionContainer { { TRP-Rx-TEGInformation-ExtIEs } } OPTIONAL,
	...
}

TRP-Rx-TEGInformation-ExtIEs F1AP-PROTOCOL-EXTENSION ::= {
	...
}

TRP-RxTx-TEGInformation ::= SEQUENCE {
	tRP-RxTx-TEGID					INTEGER (0..255),
	tRP-RxTx-TimingErrorMargin		RxTxTimingErrorMargin,
	iE-Extensions		ProtocolExtensionContainer { { TRP-RxTx-TEGInformation-ExtIEs } } OPTIONAL,
	...
}

TRP-RxTx-TEGInformation-ExtIEs F1AP-PROTOCOL-EXTENSION ::= {
	...
}


TRP-Tx-TEGInformation ::= SEQUENCE {
	tRP-Tx-TEGID					INTEGER (0..7),
	tRP-Tx-TimingErrorMargin		TimingErrorMargin,
	iE-Extensions		ProtocolExtensionContainer { { TRP-Tx-TEGInformation-ExtIEs } } OPTIONAL,
	...
}

TRP-Tx-TEGInformation-ExtIEs F1AP-PROTOCOL-EXTENSION ::= {
	...
}

TRPTxTEGAssociation ::= SEQUENCE (SIZE(1.. maxnoTRPTEGs)) OF TRPTEG-Item

TRPTEG-Item ::= SEQUENCE {
		tRP-Tx-TEGInformation		TRP-Tx-TEGInformation,
		dl-PRSResourceSetID			PRS-Resource-Set-ID,
		dl-PRSResourceID-List	SEQUENCE (SIZE(1.. maxnoofPRS-ResourcesPerSet)) OF DLPRSResourceID-Item OPTIONAL,
	iE-Extensions					ProtocolExtensionContainer { { TRPTEGItem-ExtIEs } } OPTIONAL,
	...
}

TRPTEGItem-ExtIEs F1AP-PROTOCOL-EXTENSION ::= {
	...
}

DLPRSResourceID-Item ::= SEQUENCE {
	dl-PRSResourceID		PRS-Resource-ID,
	iE-Extensions			ProtocolExtensionContainer { { DLPRSResource-Item-ExtIEs} }	OPTIONAL,
	...
}

DLPRSResource-Item-ExtIEs F1AP-PROTOCOL-EXTENSION ::= {
	...
}


TypeOfError ::= ENUMERATED {
	not-understood,
	missing,
	...
}

Transport-Layer-Address-Info ::= SEQUENCE {
	transport-UP-Layer-Address-Info-To-Add-List		Transport-UP-Layer-Address-Info-To-Add-List							OPTIONAL,
	transport-UP-Layer-Address-Info-To-Remove-List	Transport-UP-Layer-Address-Info-To-Remove-List					OPTIONAL,
	iE-Extensions	ProtocolExtensionContainer { { Transport-Layer-Address-Info-ExtIEs } }								OPTIONAL
}

Transport-Layer-Address-Info-ExtIEs 	F1AP-PROTOCOL-EXTENSION ::= {
	...
}

TRPType ::= ENUMERATED {
	prsOnlyTP,
	srsOnlyRP,
	tp,
	rp,
	trp,
	...
}

TSCAssistanceInformation ::= SEQUENCE {
	periodicity				Periodicity,
	burstArrivalTime		BurstArrivalTime													OPTIONAL,
	iE-Extensions			ProtocolExtensionContainer { {TSCAssistanceInformation-ExtIEs} }	OPTIONAL,
	...
}

TSCAssistanceInformation-ExtIEs F1AP-PROTOCOL-EXTENSION ::= {
	{ ID id-SurvivalTime	CRITICALITY ignore	EXTENSION SurvivalTime	PRESENCE optional },
	...
}

TSCTrafficCharacteristics ::= SEQUENCE {
	tSCAssistanceInformationDL		TSCAssistanceInformation								OPTIONAL,
	tSCAssistanceInformationUL		TSCAssistanceInformation								OPTIONAL,
	iE-Extensions		ProtocolExtensionContainer { {TSCTrafficCharacteristics-ExtIEs} }	OPTIONAL,
	...
}

TSCTrafficCharacteristics-ExtIEs F1AP-PROTOCOL-EXTENSION ::= {
	...
}

TRP-MeasurementUpdateList ::= SEQUENCE (SIZE (1..maxNoOfMeasTRPs)) OF TRP-MeasurementUpdateItem

TRP-MeasurementUpdateItem ::= SEQUENCE {
	tRP-ID						TRPID,
	aoA-window-information		AoA-AssistanceInfo	OPTIONAL,
	iE-extensions				ProtocolExtensionContainer { { TRP-MeasurementUpdateItem-ExtIEs } } OPTIONAL,
	...
}

TRP-MeasurementUpdateItem-ExtIEs F1AP-PROTOCOL-EXTENSION ::= {
	{ ID id-NumberOfTRPRxTEG		CRITICALITY ignore EXTENSION NumberOfTRPRxTEG		PRESENCE optional }|
	{ ID id-NumberOfTRPRxTxTEG		CRITICALITY ignore EXTENSION NumberOfTRPRxTxTEG		PRESENCE optional },
	...
}

TwoPHRModeMCG ::= ENUMERATED {enabled, ...}

TwoPHRModeSCG ::= ENUMERATED {enabled, ...}


-- U
UAC-Assistance-Info ::= SEQUENCE {
	uACPLMN-List		UACPLMN-List,
	iE-Extensions		ProtocolExtensionContainer { { UAC-Assistance-InfoExtIEs} } OPTIONAL
}

UAC-Assistance-InfoExtIEs F1AP-PROTOCOL-EXTENSION ::= {
	...
}

UACPLMN-List ::= SEQUENCE (SIZE(1..maxnoofUACPLMNs)) OF UACPLMN-Item

UACPLMN-Item::= SEQUENCE {
	pLMNIdentity				PLMN-Identity,
	uACType-List				UACType-List,	iE-Extensions		ProtocolExtensionContainer { { UACPLMN-Item-ExtIEs} } OPTIONAL
}

UACPLMN-Item-ExtIEs F1AP-PROTOCOL-EXTENSION ::= {
	{ ID id-NID	CRITICALITY ignore	EXTENSION NID	PRESENCE optional },
	...
}

UACType-List ::= SEQUENCE (SIZE(1..maxnoofUACperPLMN)) OF UACType-Item

UACType-Item::= SEQUENCE {
	uACReductionIndication 		UACReductionIndication,
	uACCategoryType				UACCategoryType,
	iE-Extensions		ProtocolExtensionContainer { { UACType-Item-ExtIEs } } OPTIONAL
}

UACType-Item-ExtIEs F1AP-PROTOCOL-EXTENSION ::= {
	...
}

UACCategoryType ::= CHOICE {
	uACstandardized				UACAction,
	uACOperatorDefined			UACOperatorDefined,
	choice-extension			ProtocolIE-SingleContainer { { UACCategoryType-ExtIEs } }
}

UACCategoryType-ExtIEs F1AP-PROTOCOL-IES ::= {
	...
}

UACOperatorDefined ::= SEQUENCE {
	accessCategory					INTEGER (32..63,...),
	accessIdentity					BIT STRING (SIZE(7)),
	iE-Extensions		ProtocolExtensionContainer { { UACOperatorDefined-ExtIEs} } OPTIONAL
}

UACOperatorDefined-ExtIEs F1AP-PROTOCOL-EXTENSION ::= {
	...
}


UACAction ::= ENUMERATED {
	reject-non-emergency-mo-dt,
	reject-rrc-cr-signalling,
	permit-emergency-sessions-and-mobile-terminated-services-only,
	permit-high-priority-sessions-and-mobile-terminated-services-only,
	...
}

UACReductionIndication ::= INTEGER (0..100)


UE-associatedLogicalF1-ConnectionItem ::= SEQUENCE {
	gNB-CU-UE-F1AP-ID		GNB-CU-UE-F1AP-ID	 OPTIONAL,
	gNB-DU-UE-F1AP-ID		GNB-DU-UE-F1AP-ID	 OPTIONAL,
	iE-Extensions			ProtocolExtensionContainer { { UE-associatedLogicalF1-ConnectionItemExtIEs} } OPTIONAL,
	...
}

UEAssistanceInformation ::= OCTET STRING

UEAssistanceInformationEUTRA ::= OCTET STRING

UE-associatedLogicalF1-ConnectionItemExtIEs F1AP-PROTOCOL-EXTENSION ::= {
	...
}

UE-CapabilityRAT-ContainerList::= OCTET STRING

UEContextNotRetrievable ::= ENUMERATED {true, ...}

UEIdentityIndexValue ::= CHOICE {
	indexLength10			BIT STRING (SIZE (10)),
	choice-extension		ProtocolIE-SingleContainer { {UEIdentityIndexValueChoice-ExtIEs} }
}

UEIdentityIndexValueChoice-ExtIEs F1AP-PROTOCOL-IES ::= {
	...
}

UEIdentity-List-For-Paging-Item		::= SEQUENCE {
	uEIdentityIndexValue						UEIdentityIndexValue,
	pagingDRX									PagingDRX		OPTIONAL,
	iE-Extensions				ProtocolExtensionContainer { { UEIdentity-List-For-Paging-Item-ExtIEs} } OPTIONAL
}

UEIdentity-List-For-Paging-Item-ExtIEs F1AP-PROTOCOL-EXTENSION ::= {
	...
}

UE-MulticastMRBs-ConfirmedToBeModified-Item::= SEQUENCE {
	mRB-ID						MRB-ID,
	mrb-type-reconfiguration	MBSPTPRetransmissionTunnelRequired			OPTIONAL,
	iE-Extensions				ProtocolExtensionContainer { { UE-MulticastMRBs-ConfirmedToBeModified-Item-ExtIEs } } OPTIONAL
}

UE-MulticastMRBs-ConfirmedToBeModified-Item-ExtIEs F1AP-PROTOCOL-EXTENSION ::= {
	...
}
UE-MulticastMRBs-RequiredToBeModified-Item::= SEQUENCE {
	mRB-ID							MRB-ID,
	mrb-type-reconfiguration		ENUMERATED {true, ...}							OPTIONAL,
	mrb-reconfigured-RLCtype		ENUMERATED {
												rlc-um-ptp,
												rlc-am-ptp,
												rlc-um-dl-ptm,
												two-rlc-um-dl-ptp-and-dl-ptm,
												three-rlc-um-dl-ptp-ul-ptp-dl-ptm,
												two-rlc-am-ptp-um-dl-ptm,
												...}								OPTIONAL,
	iE-Extensions					ProtocolExtensionContainer { { UE-MulticastMRBs-RequiredToBeModified-Item-ExtIEs } } OPTIONAL
}

UE-MulticastMRBs-RequiredToBeModified-Item-ExtIEs F1AP-PROTOCOL-EXTENSION ::= {
	{ ID id-MulticastF1UContextReferenceCU				CRITICALITY reject	EXTENSION MulticastF1UContextReferenceCU					PRESENCE optional},
	...
}

UE-MulticastMRBs-RequiredToBeReleased-Item::= SEQUENCE {
	mRB-ID					MRB-ID,
	iE-Extensions			ProtocolExtensionContainer { { UE-MulticastMRBs-RequiredToBeReleased-Item-ExtIEs } } OPTIONAL
}

UE-MulticastMRBs-RequiredToBeReleased-Item-ExtIEs F1AP-PROTOCOL-EXTENSION ::= {
	...
}

UE-MulticastMRBs-Setup-Item	::= SEQUENCE {
	mRB-ID							MRB-ID,
	multicastF1UContextReferenceCU	MulticastF1UContextReferenceCU	OPTIONAL,
	iE-Extensions					ProtocolExtensionContainer { { UE-MulticastMRBs-Setup-Item-ExtIEs } } OPTIONAL
}

UE-MulticastMRBs-Setup-Item-ExtIEs F1AP-PROTOCOL-EXTENSION ::= {
	...
}

UE-MulticastMRBs-ToBeReleased-Item	::= SEQUENCE {
	mRB-ID					MRB-ID,
	iE-Extensions			ProtocolExtensionContainer { { UE-MulticastMRBs-ToBeReleased-Item-ExtIEs } } OPTIONAL
}

UE-MulticastMRBs-ToBeReleased-Item-ExtIEs F1AP-PROTOCOL-EXTENSION ::= {
	...
}

UE-MulticastMRBs-ToBeSetup-Item	::= SEQUENCE {
	mRB-ID									MRB-ID,
	mbsPTPRetransmissionTunnelRequired		MBSPTPRetransmissionTunnelRequired			OPTIONAL,
	mbsPTPForwardingRequiredInformation		MRB-ProgressInformation						OPTIONAL,
	iE-Extensions			ProtocolExtensionContainer { { UE-MulticastMRBs-ToBeSetup-Item-ExtIEs } } OPTIONAL
}

UE-MulticastMRBs-ToBeSetup-Item-ExtIEs F1AP-PROTOCOL-EXTENSION ::= {
	{ ID id-Source-MRB-ID		CRITICALITY ignore EXTENSION MRB-ID		PRESENCE optional },
	...
}

UE-MulticastMRBs-ToBeSetup-atModify-Item	::= SEQUENCE {
	mRB-ID									MRB-ID,
	mbsPTPRetransmissionTunnelRequired		MBSPTPRetransmissionTunnelRequired			OPTIONAL,
	mbsPTPForwardingRequiredInformation		MRB-ProgressInformation						OPTIONAL,
	iE-Extensions			ProtocolExtensionContainer { { UE-MulticastMRBs-ToBeSetup-atModify-Item-ExtIEs } } OPTIONAL
}

UE-MulticastMRBs-ToBeSetup-atModify-Item-ExtIEs F1AP-PROTOCOL-EXTENSION ::= {
	...
}


UEPagingCapability ::= SEQUENCE {
	iNACTIVEStatePODetermination						ENUMERATED {supported, ...} 	OPTIONAL,
	iE-Extension				ProtocolExtensionContainer { { UEPagingCapability-ExtIEs} } 		OPTIONAL,
	...
}

UEPagingCapability-ExtIEs F1AP-PROTOCOL-EXTENSION ::= {
	{	ID id-RedCapIndication		CRITICALITY ignore 	EXTENSION RedCapIndication		PRESENCE optional },
	...
}

UEReportingInformation::= SEQUENCE {
	reportingAmount				ENUMERATED {ma0, ma1, ma2, ma4, ma8, ma16, ma32, ma64},
	reportingInterval			ENUMERATED {none, one, two, four, eight, ten, sixteen, twenty, thirty-two, sixty-four, ...},
	iE-extensions			ProtocolExtensionContainer { { UEReportingInformation-ExtIEs } }	OPTIONAL,
	...
}


UEReportingInformation-ExtIEs F1AP-PROTOCOL-EXTENSION ::= {
	...
}
UlTxDirectCurrentMoreCarrierInformation::= OCTET STRING

UL-AoA ::= SEQUENCE {
	azimuthAoA					INTEGER (0..3599),
	zenithAoA					INTEGER (0..1799)		OPTIONAL,
	lCS-to-GCS-Translation	LCS-to-GCS-Translation		OPTIONAL,
	iE-extensions			ProtocolExtensionContainer { { UL-AoA-ExtIEs } }	OPTIONAL,
	...
}

UL-AoA-ExtIEs F1AP-PROTOCOL-EXTENSION ::= {
	...
}

UL-BH-Non-UP-Traffic-Mapping ::= SEQUENCE {
	uL-BH-Non-UP-Traffic-Mapping-List			UL-BH-Non-UP-Traffic-Mapping-List,
	iE-Extensions	ProtocolExtensionContainer { { UL-BH-Non-UP-Traffic-Mapping-ExtIEs } } OPTIONAL
}

UL-BH-Non-UP-Traffic-Mapping-ExtIEs	F1AP-PROTOCOL-EXTENSION ::= {
	...
}

UL-BH-Non-UP-Traffic-Mapping-List ::= SEQUENCE (SIZE(1..maxnoofNonUPTrafficMappings)) OF UL-BH-Non-UP-Traffic-Mapping-Item

UL-BH-Non-UP-Traffic-Mapping-Item ::= SEQUENCE {
	nonUPTrafficType				NonUPTrafficType,
	bHInfo						BHInfo,
	iE-Extensions					ProtocolExtensionContainer { { UL-BH-Non-UP-Traffic-Mapping-ItemExtIEs } }	OPTIONAL
}

UL-BH-Non-UP-Traffic-Mapping-ItemExtIEs F1AP-PROTOCOL-EXTENSION ::= {
	...
}

ULConfiguration ::= SEQUENCE	{
	uLUEConfiguration		ULUEConfiguration,
	iE-Extensions	ProtocolExtensionContainer { { ULConfigurationExtIEs } }	OPTIONAL,
	...
}
ULConfigurationExtIEs 	F1AP-PROTOCOL-EXTENSION ::= {
	...
}

UL-GapFR2-Config ::= OCTET STRING

UL-RTOA-Measurement ::= SEQUENCE {
	uL-RTOA-MeasurementItem		UL-RTOA-MeasurementItem,
	additionalPath-List			AdditionalPath-List OPTIONAL,
	iE-Extensions				ProtocolExtensionContainer { { UL-RTOA-Measurement-ExtIEs } }	OPTIONAL
}

UL-RTOA-Measurement-ExtIEs 	F1AP-PROTOCOL-EXTENSION ::= {
	{ ID id-ExtendedAdditionalPathList	CRITICALITY ignore EXTENSION ExtendedAdditionalPathList	PRESENCE optional}|
	{ ID id-TRPRx-TEGInformation		CRITICALITY ignore EXTENSION TRP-Rx-TEGInformation		PRESENCE optional},
	...
}

UL-RTOA-MeasurementItem ::= CHOICE {
	k0					INTEGER (0..1970049),
	k1					INTEGER (0..985025),
	k2					INTEGER (0..492513),
	k3					INTEGER (0..246257),
	k4					INTEGER (0..123129),
	k5					INTEGER (0..61565),
	choice-extension			ProtocolIE-SingleContainer { { UL-RTOA-MeasurementItem-ExtIEs } }
}

UL-RTOA-MeasurementItem-ExtIEs F1AP-PROTOCOL-IES ::= {
	...
}

UL-SRS-RSRP ::= INTEGER (0..126)

UL-SRS-RSRPP ::= SEQUENCE {
	firstPathRSRPP				INTEGER (0..126),
	iE-extensions			ProtocolExtensionContainer { { UL-SRS-RSRPP-ExtIEs } }	OPTIONAL,
	...
}

UL-SRS-RSRPP-ExtIEs F1AP-PROTOCOL-EXTENSION ::= {
	...
}


ULUEConfiguration ::= ENUMERATED {no-data, shared, only, ...}

UL-UP-TNL-Information-to-Update-List-Item	::= SEQUENCE {
	uLUPTNLInformation		UPTransportLayerInformation,
	newULUPTNLInformation	UPTransportLayerInformation		OPTIONAL,
	bHInfo	BHInfo,
	iE-Extensions	ProtocolExtensionContainer { { UL-UP-TNL-Information-to-Update-List-ItemExtIEs } }	OPTIONAL,
	...
}

UL-UP-TNL-Information-to-Update-List-ItemExtIEs 	F1AP-PROTOCOL-EXTENSION ::= {
	...
}

UL-UP-TNL-Address-to-Update-List-Item	::= SEQUENCE {
	oldIPAdress						TransportLayerAddress,
	newIPAdress						TransportLayerAddress,
	iE-Extensions	ProtocolExtensionContainer { { UL-UP-TNL-Address-to-Update-List-ItemExtIEs } }	OPTIONAL,
	...
}

UL-UP-TNL-Address-to-Update-List-ItemExtIEs 	F1AP-PROTOCOL-EXTENSION ::= {
	...
}

ULUPTNLInformation-ToBeSetup-List ::= SEQUENCE (SIZE(1..maxnoofULUPTNLInformation)) OF ULUPTNLInformation-ToBeSetup-Item

ULUPTNLInformation-ToBeSetup-Item ::=SEQUENCE {
	uLUPTNLInformation		UPTransportLayerInformation,
	iE-Extensions	ProtocolExtensionContainer { { ULUPTNLInformation-ToBeSetup-ItemExtIEs } }	OPTIONAL,
	...
}

ULUPTNLInformation-ToBeSetup-ItemExtIEs 	F1AP-PROTOCOL-EXTENSION ::= {
	{ ID id-BHInfo			CRITICALITY ignore	EXTENSION BHInfo			PRESENCE optional	}|
	{ ID id-DRBMappingInfo	CRITICALITY ignore	EXTENSION UuRLCChannelID	PRESENCE optional	},
	...
}

Uncertainty ::= INTEGER (0..32767, ...)

UplinkChannelBW-PerSCS-List ::= SEQUENCE (SIZE (1..maxnoSCSs)) OF SCS-SpecificCarrier

UplinkTxDirectCurrentListInformation ::= OCTET STRING

UplinkTxDirectCurrentTwoCarrierListInfo ::= OCTET STRING

UPTransportLayerInformation		::= CHOICE {
	gTPTunnel		GTPTunnel,
	choice-extension			ProtocolIE-SingleContainer { { UPTransportLayerInformation-ExtIEs} }
}

UPTransportLayerInformation-ExtIEs F1AP-PROTOCOL-IES ::= {
	...
}

URI-address ::= VisibleString

Uncertainty-range-AoA ::= INTEGER (0..3599)

Uncertainty-range-ZoA ::= INTEGER (0..1799)


UuRLCChannelID ::= BIT STRING (SIZE (16))

UuRLCChannelQoSInformation ::= CHOICE {
	uuRLCChannelQoS					QoSFlowLevelQoSParameters,
	uuControlPlaneTrafficType		ENUMERATED {srb0,srb1,srb2,...},
	choice-extension		ProtocolIE-SingleContainer { { UuRLCChannelQoSInformation-ExtIEs} }
}

UuRLCChannelQoSInformation-ExtIEs F1AP-PROTOCOL-IES ::= {
	...
}

UuRLCChannelToBeSetupList ::= SEQUENCE (SIZE(1.. maxnoofUuRLCChannels)) OF UuRLCChannelToBeSetupItem

UuRLCChannelToBeSetupItem ::= SEQUENCE {
	uuRLCChannelID					UuRLCChannelID,
	uuRLCChannelQoSInformation		UuRLCChannelQoSInformation,
	rLCMode							RLCMode,
	iE-Extensions					ProtocolExtensionContainer { { UuRLCChannelToBeSetupItem-ExtIEs } }	OPTIONAL,
	...
}

UuRLCChannelToBeSetupItem-ExtIEs	F1AP-PROTOCOL-EXTENSION ::= {
	...
}

UuRLCChannelToBeModifiedList ::= SEQUENCE (SIZE(1.. maxnoofUuRLCChannels)) OF UuRLCChannelToBeModifiedItem

UuRLCChannelToBeModifiedItem ::= SEQUENCE {
	uuRLCChannelID					UuRLCChannelID,
	uuRLCChannelQoSInformation		UuRLCChannelQoSInformation			OPTIONAL,
	rLCMode							RLCMode			OPTIONAL,
	iE-Extensions					ProtocolExtensionContainer { { UuRLCChannelToBeModifiedItem-ExtIEs } }	OPTIONAL,
	...
}

UuRLCChannelToBeModifiedItem-ExtIEs	F1AP-PROTOCOL-EXTENSION ::= {
	...
}

UuRLCChannelToBeReleasedList ::= SEQUENCE (SIZE(1.. maxnoofUuRLCChannels)) OF UuRLCChannelToBeReleasedItem

UuRLCChannelToBeReleasedItem ::= SEQUENCE {
	uuRLCChannelID			UuRLCChannelID,
	iE-Extensions			ProtocolExtensionContainer { { UuRLCChannelToBeReleasedItem-ExtIEs } }	OPTIONAL,
	...
}

UuRLCChannelToBeReleasedItem-ExtIEs	F1AP-PROTOCOL-EXTENSION ::= {
	...
}

UuRLCChannelSetupList ::= SEQUENCE (SIZE(1.. maxnoofUuRLCChannels)) OF UuRLCChannelSetupItem

UuRLCChannelSetupItem ::= SEQUENCE {
	uuRLCChannelID			UuRLCChannelID,
	iE-Extensions			ProtocolExtensionContainer { { UuRLCChannelSetupItem-ExtIEs } }	OPTIONAL,
	...
}

UuRLCChannelSetupItem-ExtIEs	F1AP-PROTOCOL-EXTENSION ::= {
	...
}

UuRLCChannelFailedToBeSetupList ::= SEQUENCE (SIZE(1.. maxnoofUuRLCChannels)) OF UuRLCChannelFailedToBeSetupItem

UuRLCChannelFailedToBeSetupItem ::= SEQUENCE {
	uuRLCChannelID			UuRLCChannelID,
	cause					Cause	OPTIONAL,
	iE-Extensions			ProtocolExtensionContainer { { UuRLCChannelFailedToBeSetupItem-ExtIEs } }	OPTIONAL,
	...
}

UuRLCChannelFailedToBeSetupItem-ExtIEs	F1AP-PROTOCOL-EXTENSION ::= {
	...
}

UuRLCChannelModifiedList ::= SEQUENCE (SIZE(1.. maxnoofUuRLCChannels)) OF UuRLCChannelModifiedItem

UuRLCChannelModifiedItem ::= SEQUENCE {
	uuRLCChannelID			UuRLCChannelID,
	iE-Extensions			ProtocolExtensionContainer { { UuRLCChannelModifiedItem-ExtIEs } }	OPTIONAL,
	...
}

UuRLCChannelModifiedItem-ExtIEs	F1AP-PROTOCOL-EXTENSION ::= {
	...
}

UuRLCChannelFailedToBeModifiedList ::= SEQUENCE (SIZE(1.. maxnoofUuRLCChannels)) OF UuRLCChannelFailedToBeModifiedItem

UuRLCChannelFailedToBeModifiedItem ::= SEQUENCE {
	uuRLCChannelID			UuRLCChannelID,
	cause					Cause	OPTIONAL,
	iE-Extensions			ProtocolExtensionContainer { { UuRLCChannelFailedToBeModifiedItem-ExtIEs } }	OPTIONAL,
	...
}

UuRLCChannelFailedToBeModifiedItem-ExtIEs	F1AP-PROTOCOL-EXTENSION ::= {
	...
}

UuRLCChannelRequiredToBeModifiedList ::= SEQUENCE (SIZE(1.. maxnoofUuRLCChannels)) OF UuRLCChannelRequiredToBeModifiedItem

UuRLCChannelRequiredToBeModifiedItem ::= SEQUENCE {
	uuRLCChannelID			UuRLCChannelID,
	iE-Extensions			ProtocolExtensionContainer { { UuRLCChannelRequiredToBeModifiedItem-ExtIEs } }	OPTIONAL,
	...
}

UuRLCChannelRequiredToBeModifiedItem-ExtIEs	F1AP-PROTOCOL-EXTENSION ::= {
	...
}

UuRLCChannelRequiredToBeReleasedList ::= SEQUENCE (SIZE(1.. maxnoofUuRLCChannels)) OF UuRLCChannelRequiredToBeReleasedItem

UuRLCChannelRequiredToBeReleasedItem ::= SEQUENCE {
	uuRLCChannelID			UuRLCChannelID,
	iE-Extensions			ProtocolExtensionContainer { { UuRLCChannelRequiredToBeReleasedItem-ExtIEs } }	OPTIONAL,
	...
}

UuRLCChannelRequiredToBeReleasedItem-ExtIEs	F1AP-PROTOCOL-EXTENSION ::= {
	...
}


-- V

VictimgNBSetID ::= SEQUENCE {
	victimgNBSetID		GNBSetID,
	iE-Extensions		ProtocolExtensionContainer { { VictimgNBSetID-ExtIEs } }		OPTIONAL
}

VictimgNBSetID-ExtIEs 	F1AP-PROTOCOL-EXTENSION ::= {
	...
}

VehicleUE ::= ENUMERATED {
	authorized,
	not-authorized,
	...
}

PedestrianUE ::= ENUMERATED {
	authorized,
	not-authorized,
	...
}

-- W

-- X

-- Y

-- Z

ZoAInformation ::= SEQUENCE {
	zenithAoA					INTEGER (0..1799),
	lCS-to-GCS-Translation	LCS-to-GCS-Translation		OPTIONAL,
	iE-extensions			ProtocolExtensionContainer { { ZoAInformation-ExtIEs } }	OPTIONAL,
	...
}

ZoAInformation-ExtIEs F1AP-PROTOCOL-EXTENSION ::= {
	...
}


END

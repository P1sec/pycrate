-- ASN1START
-- **************************************************************
--
-- Elementary Procedure definitions
--
-- **************************************************************

F1AP-PDU-Descriptions  {
itu-t (0) identified-organization (4) etsi (0) mobileDomain (0)
ngran-access (22) modules (3) f1ap (3) version1 (1) f1ap-PDU-Descriptions (0)}

DEFINITIONS AUTOMATIC TAGS ::=

BEGIN

-- **************************************************************
--
-- IE parameter types from other modules.
--
-- **************************************************************

IMPORTS
	Criticality,
	ProcedureCode

FROM F1AP-CommonDataTypes
	Reset,
	ResetAcknowledge,
	F1SetupRequest,
	F1SetupResponse,
	F1SetupFailure,
	GNBDUConfigurationUpdate,
	GNBDUConfigurationUpdateAcknowledge,
	GNBDUConfigurationUpdateFailure,
	GNBCUConfigurationUpdate,
	GNBCUConfigurationUpdateAcknowledge,
	GNBCUConfigurationUpdateFailure,
	UEContextSetupRequest,
	UEContextSetupResponse,
	UEContextSetupFailure,
	UEContextReleaseCommand,
	UEContextReleaseComplete,
	UEContextModificationRequest,
	UEContextModificationResponse,
	UEContextModificationFailure,
	UEContextModificationRequired,
	UEContextModificationConfirm,
	ErrorIndication,
	UEContextReleaseRequest,
	DLRRCMessageTransfer,
	ULRRCMessageTransfer,
	GNBDUResourceCoordinationRequest,
	GNBDUResourceCoordinationResponse,
	PrivateMessage,
	UEInactivityNotification,
	InitialULRRCMessageTransfer,
	SystemInformationDeliveryCommand,
	Paging,
	Notify,
	WriteReplaceWarningRequest,
	WriteReplaceWarningResponse,
	PWSCancelRequest,
	PWSCancelResponse,
	PWSRestartIndication,
	PWSFailureIndication,
	GNBDUStatusIndication,
	RRCDeliveryReport,
	UEContextModificationRefuse,
	F1RemovalRequest,
	F1RemovalResponse,
	F1RemovalFailure,
	NetworkAccessRateReduction,
	TraceStart,
	DeactivateTrace,
	DUCURadioInformationTransfer,
	CUDURadioInformationTransfer,
	BAPMappingConfiguration,
	BAPMappingConfigurationAcknowledge,
	BAPMappingConfigurationFailure,
	GNBDUResourceConfiguration,
	GNBDUResourceConfigurationAcknowledge,
	GNBDUResourceConfigurationFailure,
	IABTNLAddressRequest,
	IABTNLAddressResponse,
	IABTNLAddressFailure,
	IABUPConfigurationUpdateRequest,
	IABUPConfigurationUpdateResponse,
	IABUPConfigurationUpdateFailure,
	ResourceStatusRequest,
	ResourceStatusResponse,
	ResourceStatusFailure,
	ResourceStatusUpdate,
	AccessAndMobilityIndication,
	ReferenceTimeInformationReportingControl,
	ReferenceTimeInformationReport,
	AccessSuccess,
	CellTrafficTrace,
	PositioningMeasurementRequest,
	PositioningMeasurementResponse,
	PositioningMeasurementFailure,
	PositioningAssistanceInformationControl,
	PositioningAssistanceInformationFeedback,
	PositioningMeasurementReport,
	PositioningMeasurementAbort,
	PositioningMeasurementFailureIndication,
	PositioningMeasurementUpdate,
	TRPInformationRequest,
	TRPInformationResponse,
	TRPInformationFailure,
	PositioningInformationRequest,
	PositioningInformationResponse,
	PositioningInformationFailure,
	PositioningActivationRequest,
	PositioningActivationResponse,
	PositioningActivationFailure,
	PositioningDeactivation,
	PositioningInformationUpdate,
	E-CIDMeasurementInitiationRequest,
	E-CIDMeasurementInitiationResponse,
	E-CIDMeasurementInitiationFailure,
	E-CIDMeasurementFailureIndication,
	E-CIDMeasurementReport,
	E-CIDMeasurementTerminationCommand,
	BroadcastContextSetupRequest,
	BroadcastContextSetupResponse,
	BroadcastContextSetupFailure,
	BroadcastContextReleaseCommand,
	BroadcastContextReleaseComplete,
	BroadcastContextReleaseRequest,
	BroadcastContextModificationRequest,
	BroadcastContextModificationResponse,
	BroadcastContextModificationFailure,
	MulticastGroupPaging,
	MulticastContextSetupRequest,
	MulticastContextSetupResponse,
	MulticastContextSetupFailure,
	MulticastContextReleaseCommand,
	MulticastContextReleaseComplete,
	MulticastContextReleaseRequest,
	MulticastContextModificationRequest,
	MulticastContextModificationResponse,
	MulticastContextModificationFailure,
	MulticastDistributionSetupRequest,
	MulticastDistributionSetupResponse,
	MulticastDistributionSetupFailure,
	MulticastDistributionReleaseCommand,
	MulticastDistributionReleaseComplete,
	PDCMeasurementInitiationRequest,
	PDCMeasurementInitiationResponse,
	PDCMeasurementInitiationFailure,
	PDCMeasurementReport,
	PDCMeasurementTerminationCommand,
	PDCMeasurementFailureIndication,
	PRSConfigurationRequest,
	PRSConfigurationResponse,
	PRSConfigurationFailure,
	MeasurementPreconfigurationRequired,
	MeasurementPreconfigurationConfirm,
	MeasurementPreconfigurationRefuse,
	MeasurementActivation,
	QoEInformationTransfer,
	PosSystemInformationDeliveryCommand




FROM F1AP-PDU-Contents
	id-Reset,
	id-F1Setup,
	id-gNBDUConfigurationUpdate,
	id-gNBCUConfigurationUpdate,
	id-UEContextSetup,
	id-UEContextRelease,
	id-UEContextModification,
	id-UEContextModificationRequired,
	id-ErrorIndication,
	id-UEContextReleaseRequest,
	id-DLRRCMessageTransfer,
	id-ULRRCMessageTransfer,
	id-GNBDUResourceCoordination,
	id-privateMessage,
	id-UEInactivityNotification,
	id-InitialULRRCMessageTransfer,
	id-SystemInformationDeliveryCommand,
	id-Paging,
	id-Notify,
	id-WriteReplaceWarning,
	id-PWSCancel,
	id-PWSRestartIndication,
	id-PWSFailureIndication,
	id-GNBDUStatusIndication,
	id-RRCDeliveryReport,
	id-F1Removal,
	id-NetworkAccessRateReduction,
	id-TraceStart,
	id-DeactivateTrace,
	id-DUCURadioInformationTransfer,
	id-CUDURadioInformationTransfer,
	id-BAPMappingConfiguration,
	id-GNBDUResourceConfiguration,
	id-IABTNLAddressAllocation,
	id-IABUPConfigurationUpdate,
	id-resourceStatusReportingInitiation,
	id-resourceStatusReporting,
	id-accessAndMobilityIndication,
	id-ReferenceTimeInformationReportingControl,
	id-ReferenceTimeInformationReport,
	id-accessSuccess,
	id-cellTrafficTrace,
	id-PositioningMeasurementExchange,
	id-PositioningAssistanceInformationControl,
	id-PositioningAssistanceInformationFeedback,
	id-PositioningMeasurementReport,
	id-PositioningMeasurementAbort,
	id-PositioningMeasurementFailureIndication,
	id-PositioningMeasurementUpdate,
	id-TRPInformationExchange,
	id-PositioningInformationExchange,
	id-PositioningActivation,
	id-PositioningDeactivation,
	id-PositioningInformationUpdate,
	id-E-CIDMeasurementInitiation,
	id-E-CIDMeasurementFailureIndication,
	id-E-CIDMeasurementReport,
	id-E-CIDMeasurementTermination,
	id-BroadcastContextSetup,
	id-BroadcastContextRelease,
	id-BroadcastContextReleaseRequest,
	id-BroadcastContextModification,
	id-MulticastGroupPaging,
	id-MulticastContextSetup,
	id-MulticastContextRelease,
	id-MulticastContextReleaseRequest,
	id-MulticastContextModification,
	id-MulticastDistributionSetup,
	id-MulticastDistributionRelease,
	id-PDCMeasurementInitiation,
	id-PDCMeasurementInitiationRequest,
	id-PDCMeasurementInitiationResponse,
	id-PDCMeasurementInitiationFailure,
	id-PDCMeasurementTerminationCommand,
	id-PDCMeasurementFailureIndication,
	id-PDCMeasurementReport,
	id-pRSConfigurationExchange,
	id-measurementPreconfiguration,
	id-measurementActivation,
	id-QoEInformationTransfer,
	id-PosSystemInformationDeliveryCommand


FROM F1AP-Constants

	ProtocolIE-SingleContainer{},
	F1AP-PROTOCOL-IES

FROM F1AP-Containers;


-- **************************************************************
--
-- Interface Elementary Procedure Class
--
-- **************************************************************

F1AP-ELEMENTARY-PROCEDURE ::= CLASS {
	&InitiatingMessage				,
	&SuccessfulOutcome							OPTIONAL,
	&UnsuccessfulOutcome						OPTIONAL,
	&procedureCode				ProcedureCode 	UNIQUE,
	&criticality				Criticality 	DEFAULT ignore
}
WITH SYNTAX {
	INITIATING MESSAGE			&InitiatingMessage
	[SUCCESSFUL OUTCOME			&SuccessfulOutcome]
	[UNSUCCESSFUL OUTCOME		&UnsuccessfulOutcome]
	PROCEDURE CODE				&procedureCode
	[CRITICALITY				&criticality]
}

-- **************************************************************
--
-- Interface PDU Definition
--
-- **************************************************************

F1AP-PDU ::= CHOICE {
	initiatingMessage	InitiatingMessage,
	successfulOutcome	SuccessfulOutcome,
	unsuccessfulOutcome	UnsuccessfulOutcome,
	choice-extension	ProtocolIE-SingleContainer { { F1AP-PDU-ExtIEs} }
}

F1AP-PDU-ExtIEs F1AP-PROTOCOL-IES ::= { -- this extension is not used
	...
}

InitiatingMessage ::= SEQUENCE {
	procedureCode	F1AP-ELEMENTARY-PROCEDURE.&procedureCode		({F1AP-ELEMENTARY-PROCEDURES}),
	criticality		F1AP-ELEMENTARY-PROCEDURE.&criticality			({F1AP-ELEMENTARY-PROCEDURES}{@procedureCode}),
	value			F1AP-ELEMENTARY-PROCEDURE.&InitiatingMessage	({F1AP-ELEMENTARY-PROCEDURES}{@procedureCode})
}

SuccessfulOutcome ::= SEQUENCE {
	procedureCode	F1AP-ELEMENTARY-PROCEDURE.&procedureCode		({F1AP-ELEMENTARY-PROCEDURES}),
	criticality		F1AP-ELEMENTARY-PROCEDURE.&criticality			({F1AP-ELEMENTARY-PROCEDURES}{@procedureCode}),
	value			F1AP-ELEMENTARY-PROCEDURE.&SuccessfulOutcome	({F1AP-ELEMENTARY-PROCEDURES}{@procedureCode})
}

UnsuccessfulOutcome ::= SEQUENCE {
	procedureCode	F1AP-ELEMENTARY-PROCEDURE.&procedureCode		({F1AP-ELEMENTARY-PROCEDURES}),
	criticality		F1AP-ELEMENTARY-PROCEDURE.&criticality			({F1AP-ELEMENTARY-PROCEDURES}{@procedureCode}),
	value			F1AP-ELEMENTARY-PROCEDURE.&UnsuccessfulOutcome	({F1AP-ELEMENTARY-PROCEDURES}{@procedureCode})
}

-- **************************************************************
--
-- Interface Elementary Procedure List
--
-- **************************************************************

F1AP-ELEMENTARY-PROCEDURES F1AP-ELEMENTARY-PROCEDURE ::= {
	F1AP-ELEMENTARY-PROCEDURES-CLASS-1			|
	F1AP-ELEMENTARY-PROCEDURES-CLASS-2,
	...
}


F1AP-ELEMENTARY-PROCEDURES-CLASS-1 F1AP-ELEMENTARY-PROCEDURE ::= {
	reset							|
	f1Setup							|
	gNBDUConfigurationUpdate		|
	gNBCUConfigurationUpdate		|
	uEContextSetup					|
	uEContextRelease				|
	uEContextModification			|
	uEContextModificationRequired	|
	writeReplaceWarning				|
	pWSCancel					|
	gNBDUResourceCoordination		|
	f1Removal						|
	bAPMappingConfiguration			|
	gNBDUResourceConfiguration		|
	iABTNLAddressAllocation			|
	iABUPConfigurationUpdate		|
	resourceStatusReportingInitiation	|
	positioningMeasurementExchange	|
	tRPInformationExchange			|
	positioningInformationExchange	|
	positioningActivation			|
	e-CIDMeasurementInitiation		|
	broadcastContextSetup			|
	broadcastContextRelease			|
	broadcastContextModification|
	multicastContextSetup			|
	multicastContextRelease		|
	multicastContextModification	|
	multicastDistributionSetup		|
	multicastDistributionRelease	|
	pDCMeasurementInitiation		|
	pRSConfigurationExchange		|
	measurementPreconfiguration	,
	...
}

F1AP-ELEMENTARY-PROCEDURES-CLASS-2 F1AP-ELEMENTARY-PROCEDURE ::= {
	errorIndication							|
	uEContextReleaseRequest					|
	dLRRCMessageTransfer					|
	uLRRCMessageTransfer					|
	uEInactivityNotification				|
	privateMessage							|
	initialULRRCMessageTransfer				|
	systemInformationDelivery				|
	paging									|
	notify									|
	pWSRestartIndication					|
	pWSFailureIndication					|
	gNBDUStatusIndication					|
	rRCDeliveryReport						|
	networkAccessRateReduction				|
	traceStart								|
	deactivateTrace							|
	dUCURadioInformationTransfer			|
	cUDURadioInformationTransfer			|
	resourceStatusReporting					|
	accessAndMobilityIndication				|
	referenceTimeInformationReportingControl|
	referenceTimeInformationReport			|
	accessSuccess							|
	cellTrafficTrace						|
	positioningAssistanceInformationControl		|
	positioningAssistanceInformationFeedback	|
	positioningMeasurementReport				|
	positioningMeasurementAbort					|
	positioningMeasurementFailureIndication		|
	positioningMeasurementUpdate				|
	positioningDeactivation						|
	e-CIDMeasurementFailureIndication			|
	e-CIDMeasurementReport						|
	e-CIDMeasurementTermination					|
	positioningInformationUpdate				|
	multicastGroupPaging						|
	broadcastContextReleaseRequest				|
	multicastContextReleaseRequest				|
	pDCMeasurementReport						|
	pDCMeasurementTerminationCommand			|
	pDCMeasurementFailureIndication				|
	measurementActivation						|
	qoEInformationTransfer						|
	posSystemInformationDelivery,
	...
}
-- **************************************************************
--
-- Interface Elementary Procedures
--
-- **************************************************************

reset F1AP-ELEMENTARY-PROCEDURE ::= {
	INITIATING MESSAGE		Reset
	SUCCESSFUL OUTCOME		ResetAcknowledge
	PROCEDURE CODE			id-Reset
	CRITICALITY				reject
}

f1Setup F1AP-ELEMENTARY-PROCEDURE ::= {
	INITIATING MESSAGE		F1SetupRequest
	SUCCESSFUL OUTCOME		F1SetupResponse
	UNSUCCESSFUL OUTCOME	F1SetupFailure
	PROCEDURE CODE			id-F1Setup
	CRITICALITY				reject
}

gNBDUConfigurationUpdate F1AP-ELEMENTARY-PROCEDURE ::= {
	INITIATING MESSAGE		GNBDUConfigurationUpdate
	SUCCESSFUL OUTCOME		GNBDUConfigurationUpdateAcknowledge
	UNSUCCESSFUL OUTCOME	GNBDUConfigurationUpdateFailure
	PROCEDURE CODE			id-gNBDUConfigurationUpdate
	CRITICALITY				reject
}

gNBCUConfigurationUpdate F1AP-ELEMENTARY-PROCEDURE ::= {
	INITIATING MESSAGE		GNBCUConfigurationUpdate
	SUCCESSFUL OUTCOME		GNBCUConfigurationUpdateAcknowledge
	UNSUCCESSFUL OUTCOME	GNBCUConfigurationUpdateFailure
	PROCEDURE CODE			id-gNBCUConfigurationUpdate
	CRITICALITY				reject
}

uEContextSetup F1AP-ELEMENTARY-PROCEDURE ::= {
	INITIATING MESSAGE		UEContextSetupRequest
	SUCCESSFUL OUTCOME		UEContextSetupResponse
	UNSUCCESSFUL OUTCOME	UEContextSetupFailure
	PROCEDURE CODE			id-UEContextSetup
	CRITICALITY				reject
}

uEContextRelease F1AP-ELEMENTARY-PROCEDURE ::= {
	INITIATING MESSAGE		UEContextReleaseCommand
	SUCCESSFUL OUTCOME		UEContextReleaseComplete
	PROCEDURE CODE			id-UEContextRelease
	CRITICALITY				reject
}

uEContextModification F1AP-ELEMENTARY-PROCEDURE ::= {
	INITIATING MESSAGE		UEContextModificationRequest
	SUCCESSFUL OUTCOME		UEContextModificationResponse
	UNSUCCESSFUL OUTCOME	UEContextModificationFailure
	PROCEDURE CODE			id-UEContextModification
	CRITICALITY				reject
}

uEContextModificationRequired F1AP-ELEMENTARY-PROCEDURE ::= {
	INITIATING MESSAGE		UEContextModificationRequired
	SUCCESSFUL OUTCOME		UEContextModificationConfirm
	UNSUCCESSFUL OUTCOME	UEContextModificationRefuse
	PROCEDURE CODE			id-UEContextModificationRequired
	CRITICALITY				reject
}

writeReplaceWarning F1AP-ELEMENTARY-PROCEDURE ::= {
	INITIATING MESSAGE		WriteReplaceWarningRequest
	SUCCESSFUL OUTCOME		WriteReplaceWarningResponse
	PROCEDURE CODE			id-WriteReplaceWarning
	CRITICALITY				reject
}

pWSCancel F1AP-ELEMENTARY-PROCEDURE ::= {
	INITIATING MESSAGE		PWSCancelRequest
	SUCCESSFUL OUTCOME		PWSCancelResponse
	PROCEDURE CODE			id-PWSCancel
	CRITICALITY				reject
}

errorIndication F1AP-ELEMENTARY-PROCEDURE ::= {
	INITIATING MESSAGE		ErrorIndication
	PROCEDURE CODE			id-ErrorIndication
	CRITICALITY				ignore
}

uEContextReleaseRequest F1AP-ELEMENTARY-PROCEDURE ::= {
	INITIATING MESSAGE		UEContextReleaseRequest
	PROCEDURE CODE			id-UEContextReleaseRequest
	CRITICALITY				ignore
}


initialULRRCMessageTransfer F1AP-ELEMENTARY-PROCEDURE ::= {
	INITIATING MESSAGE		InitialULRRCMessageTransfer
	PROCEDURE CODE			id-InitialULRRCMessageTransfer
	CRITICALITY				ignore
}

dLRRCMessageTransfer F1AP-ELEMENTARY-PROCEDURE ::= {
	INITIATING MESSAGE		DLRRCMessageTransfer
	PROCEDURE CODE			id-DLRRCMessageTransfer
	CRITICALITY				ignore
}

uLRRCMessageTransfer F1AP-ELEMENTARY-PROCEDURE ::= {
	INITIATING MESSAGE		ULRRCMessageTransfer
	PROCEDURE CODE			id-ULRRCMessageTransfer
	CRITICALITY				ignore
}


uEInactivityNotification  F1AP-ELEMENTARY-PROCEDURE ::= {
	INITIATING MESSAGE		UEInactivityNotification
	PROCEDURE CODE			id-UEInactivityNotification
	CRITICALITY				ignore
}

gNBDUResourceCoordination F1AP-ELEMENTARY-PROCEDURE ::= {
	INITIATING MESSAGE		GNBDUResourceCoordinationRequest
	SUCCESSFUL OUTCOME		GNBDUResourceCoordinationResponse
	PROCEDURE CODE			id-GNBDUResourceCoordination
	CRITICALITY				reject
}

privateMessage F1AP-ELEMENTARY-PROCEDURE ::= {
	INITIATING MESSAGE		PrivateMessage
	PROCEDURE CODE			id-privateMessage
	CRITICALITY				ignore
}

systemInformationDelivery F1AP-ELEMENTARY-PROCEDURE ::= {
	INITIATING MESSAGE		SystemInformationDeliveryCommand
	PROCEDURE CODE			id-SystemInformationDeliveryCommand
	CRITICALITY				ignore
}


paging F1AP-ELEMENTARY-PROCEDURE ::= {
	INITIATING MESSAGE		Paging
	PROCEDURE CODE			id-Paging
	CRITICALITY				ignore
}

notify F1AP-ELEMENTARY-PROCEDURE ::= {
	INITIATING MESSAGE		Notify
	PROCEDURE CODE			id-Notify
	CRITICALITY				ignore
}

networkAccessRateReduction F1AP-ELEMENTARY-PROCEDURE ::= {
	INITIATING MESSAGE		NetworkAccessRateReduction
	PROCEDURE CODE			id-NetworkAccessRateReduction
	CRITICALITY				ignore
}


pWSRestartIndication F1AP-ELEMENTARY-PROCEDURE ::= {
	INITIATING MESSAGE		PWSRestartIndication
	PROCEDURE CODE			id-PWSRestartIndication
	CRITICALITY				ignore
}

pWSFailureIndication F1AP-ELEMENTARY-PROCEDURE ::= {
	INITIATING MESSAGE		PWSFailureIndication
	PROCEDURE CODE			id-PWSFailureIndication
	CRITICALITY				ignore
}

gNBDUStatusIndication 	F1AP-ELEMENTARY-PROCEDURE ::= {
	INITIATING MESSAGE		GNBDUStatusIndication
	PROCEDURE CODE			id-GNBDUStatusIndication
	CRITICALITY				ignore
}


rRCDeliveryReport F1AP-ELEMENTARY-PROCEDURE ::= {
	INITIATING MESSAGE		RRCDeliveryReport
	PROCEDURE CODE			id-RRCDeliveryReport
	CRITICALITY				ignore
}

f1Removal F1AP-ELEMENTARY-PROCEDURE ::= {
	INITIATING MESSAGE		F1RemovalRequest
	SUCCESSFUL OUTCOME		F1RemovalResponse
	UNSUCCESSFUL OUTCOME	F1RemovalFailure
	PROCEDURE CODE			id-F1Removal
	CRITICALITY				reject
}

traceStart F1AP-ELEMENTARY-PROCEDURE ::= {
	INITIATING MESSAGE		TraceStart
	PROCEDURE CODE			id-TraceStart
	CRITICALITY				ignore
}

deactivateTrace F1AP-ELEMENTARY-PROCEDURE ::= {
	INITIATING MESSAGE		DeactivateTrace
	PROCEDURE CODE			id-DeactivateTrace
	CRITICALITY				ignore
}

dUCURadioInformationTransfer F1AP-ELEMENTARY-PROCEDURE ::= {
	INITIATING MESSAGE		DUCURadioInformationTransfer
	PROCEDURE CODE			id-DUCURadioInformationTransfer
	CRITICALITY				ignore
}

cUDURadioInformationTransfer F1AP-ELEMENTARY-PROCEDURE ::= {
	INITIATING MESSAGE		CUDURadioInformationTransfer
	PROCEDURE CODE			id-CUDURadioInformationTransfer
	CRITICALITY				ignore
}

bAPMappingConfiguration F1AP-ELEMENTARY-PROCEDURE ::= {
	INITIATING MESSAGE		BAPMappingConfiguration
	SUCCESSFUL OUTCOME		BAPMappingConfigurationAcknowledge
	UNSUCCESSFUL OUTCOME	BAPMappingConfigurationFailure
	PROCEDURE CODE			id-BAPMappingConfiguration
	CRITICALITY				reject
}

gNBDUResourceConfiguration F1AP-ELEMENTARY-PROCEDURE ::= {
	INITIATING MESSAGE		GNBDUResourceConfiguration
	SUCCESSFUL OUTCOME		GNBDUResourceConfigurationAcknowledge
	UNSUCCESSFUL OUTCOME	GNBDUResourceConfigurationFailure
	PROCEDURE CODE			id-GNBDUResourceConfiguration
	CRITICALITY				reject
}

iABTNLAddressAllocation F1AP-ELEMENTARY-PROCEDURE ::= {
	INITIATING MESSAGE		IABTNLAddressRequest
	SUCCESSFUL OUTCOME		IABTNLAddressResponse
	UNSUCCESSFUL OUTCOME	IABTNLAddressFailure
	PROCEDURE CODE			id-IABTNLAddressAllocation
	CRITICALITY				reject
}

iABUPConfigurationUpdate F1AP-ELEMENTARY-PROCEDURE ::= {
	INITIATING MESSAGE		IABUPConfigurationUpdateRequest
	SUCCESSFUL OUTCOME		IABUPConfigurationUpdateResponse
	UNSUCCESSFUL OUTCOME	IABUPConfigurationUpdateFailure
	PROCEDURE CODE			id-IABUPConfigurationUpdate
	CRITICALITY				reject
}

resourceStatusReportingInitiation F1AP-ELEMENTARY-PROCEDURE ::= {
	INITIATING MESSAGE		ResourceStatusRequest
	SUCCESSFUL OUTCOME		ResourceStatusResponse
	UNSUCCESSFUL OUTCOME	ResourceStatusFailure
	PROCEDURE CODE			id-resourceStatusReportingInitiation
	CRITICALITY				reject
}

resourceStatusReporting F1AP-ELEMENTARY-PROCEDURE ::= {
	INITIATING MESSAGE		ResourceStatusUpdate
	PROCEDURE CODE			id-resourceStatusReporting
	CRITICALITY				ignore
}

accessAndMobilityIndication F1AP-ELEMENTARY-PROCEDURE ::= {
	INITIATING MESSAGE		AccessAndMobilityIndication
	PROCEDURE CODE			id-accessAndMobilityIndication
	CRITICALITY				ignore
}

referenceTimeInformationReportingControl F1AP-ELEMENTARY-PROCEDURE ::= {
	INITIATING MESSAGE		ReferenceTimeInformationReportingControl
	PROCEDURE CODE			id-ReferenceTimeInformationReportingControl
	CRITICALITY				ignore
}

referenceTimeInformationReport F1AP-ELEMENTARY-PROCEDURE ::= {
	INITIATING MESSAGE		ReferenceTimeInformationReport
	PROCEDURE CODE			id-ReferenceTimeInformationReport
	CRITICALITY				ignore
}

accessSuccess F1AP-ELEMENTARY-PROCEDURE ::= {
	INITIATING MESSAGE		AccessSuccess
	PROCEDURE CODE			id-accessSuccess
	CRITICALITY				ignore
}

cellTrafficTrace F1AP-ELEMENTARY-PROCEDURE ::= {
	INITIATING MESSAGE		CellTrafficTrace
	PROCEDURE CODE			id-cellTrafficTrace
	CRITICALITY				ignore
}

positioningAssistanceInformationControl F1AP-ELEMENTARY-PROCEDURE ::= {
	INITIATING MESSAGE		PositioningAssistanceInformationControl
	PROCEDURE CODE			id-PositioningAssistanceInformationControl
	CRITICALITY				ignore
}

positioningAssistanceInformationFeedback F1AP-ELEMENTARY-PROCEDURE ::= {
	INITIATING MESSAGE		PositioningAssistanceInformationFeedback
	PROCEDURE CODE			id-PositioningAssistanceInformationFeedback
	CRITICALITY				ignore
}

positioningMeasurementExchange F1AP-ELEMENTARY-PROCEDURE ::= {
	INITIATING MESSAGE		PositioningMeasurementRequest
	SUCCESSFUL OUTCOME		PositioningMeasurementResponse
	UNSUCCESSFUL OUTCOME	PositioningMeasurementFailure
	PROCEDURE CODE			id-PositioningMeasurementExchange
	CRITICALITY				reject
}

positioningMeasurementReport F1AP-ELEMENTARY-PROCEDURE ::= {
	INITIATING MESSAGE		PositioningMeasurementReport
	PROCEDURE CODE			id-PositioningMeasurementReport
	CRITICALITY				ignore
}

positioningMeasurementAbort F1AP-ELEMENTARY-PROCEDURE ::= {
	INITIATING MESSAGE		PositioningMeasurementAbort
	PROCEDURE CODE			id-PositioningMeasurementAbort
	CRITICALITY				ignore
}

positioningMeasurementFailureIndication F1AP-ELEMENTARY-PROCEDURE ::= {
	INITIATING MESSAGE		PositioningMeasurementFailureIndication
	PROCEDURE CODE			id-PositioningMeasurementFailureIndication
	CRITICALITY				ignore
}

positioningMeasurementUpdate F1AP-ELEMENTARY-PROCEDURE ::= {
	INITIATING MESSAGE		PositioningMeasurementUpdate
	PROCEDURE CODE			id-PositioningMeasurementUpdate
	CRITICALITY				ignore
}


tRPInformationExchange F1AP-ELEMENTARY-PROCEDURE ::= {
	INITIATING MESSAGE		TRPInformationRequest
	SUCCESSFUL OUTCOME		TRPInformationResponse
	UNSUCCESSFUL OUTCOME	TRPInformationFailure
	PROCEDURE CODE			id-TRPInformationExchange
	CRITICALITY				reject
}

positioningInformationExchange F1AP-ELEMENTARY-PROCEDURE ::= {
	INITIATING MESSAGE		PositioningInformationRequest
	SUCCESSFUL OUTCOME		PositioningInformationResponse
	UNSUCCESSFUL OUTCOME	PositioningInformationFailure
	PROCEDURE CODE			id-PositioningInformationExchange
	CRITICALITY				reject
}

positioningActivation F1AP-ELEMENTARY-PROCEDURE ::= {
	INITIATING MESSAGE		PositioningActivationRequest
	SUCCESSFUL OUTCOME		PositioningActivationResponse
	UNSUCCESSFUL OUTCOME	PositioningActivationFailure
	PROCEDURE CODE			id-PositioningActivation
	CRITICALITY				reject
}

positioningDeactivation F1AP-ELEMENTARY-PROCEDURE ::= {
	INITIATING MESSAGE		PositioningDeactivation
	PROCEDURE CODE			id-PositioningDeactivation
	CRITICALITY				ignore
}

e-CIDMeasurementInitiation F1AP-ELEMENTARY-PROCEDURE ::= {
	INITIATING MESSAGE		E-CIDMeasurementInitiationRequest
	SUCCESSFUL OUTCOME		E-CIDMeasurementInitiationResponse
	UNSUCCESSFUL OUTCOME	E-CIDMeasurementInitiationFailure
	PROCEDURE CODE			id-E-CIDMeasurementInitiation
	CRITICALITY				reject
}

e-CIDMeasurementFailureIndication F1AP-ELEMENTARY-PROCEDURE ::= {
	INITIATING MESSAGE		E-CIDMeasurementFailureIndication
	PROCEDURE CODE			id-E-CIDMeasurementFailureIndication
	CRITICALITY				ignore
}

e-CIDMeasurementReport F1AP-ELEMENTARY-PROCEDURE ::= {
	INITIATING MESSAGE		E-CIDMeasurementReport
	PROCEDURE CODE			id-E-CIDMeasurementReport
	CRITICALITY				ignore
}

e-CIDMeasurementTermination F1AP-ELEMENTARY-PROCEDURE ::= {
	INITIATING MESSAGE		E-CIDMeasurementTerminationCommand
	PROCEDURE CODE			id-E-CIDMeasurementTermination
	CRITICALITY				ignore
}

positioningInformationUpdate F1AP-ELEMENTARY-PROCEDURE ::= {
	INITIATING MESSAGE		PositioningInformationUpdate
	PROCEDURE CODE			id-PositioningInformationUpdate
	CRITICALITY				ignore
}

broadcastContextSetup F1AP-ELEMENTARY-PROCEDURE ::= {
	INITIATING MESSAGE		BroadcastContextSetupRequest
	SUCCESSFUL OUTCOME		BroadcastContextSetupResponse
	UNSUCCESSFUL OUTCOME	BroadcastContextSetupFailure
	PROCEDURE CODE			id-BroadcastContextSetup
	CRITICALITY				reject
}

broadcastContextRelease F1AP-ELEMENTARY-PROCEDURE ::= {
	INITIATING MESSAGE		BroadcastContextReleaseCommand
	SUCCESSFUL OUTCOME		BroadcastContextReleaseComplete
	PROCEDURE CODE			id-BroadcastContextRelease
	CRITICALITY				reject
}

broadcastContextReleaseRequest F1AP-ELEMENTARY-PROCEDURE ::= {
	INITIATING MESSAGE		BroadcastContextReleaseRequest
	PROCEDURE CODE			id-BroadcastContextReleaseRequest
	CRITICALITY				reject
}

broadcastContextModification F1AP-ELEMENTARY-PROCEDURE ::= {
	INITIATING MESSAGE		BroadcastContextModificationRequest
	SUCCESSFUL OUTCOME		BroadcastContextModificationResponse
	UNSUCCESSFUL OUTCOME	BroadcastContextModificationFailure
	PROCEDURE CODE			id-BroadcastContextModification
	CRITICALITY				reject
}

multicastGroupPaging F1AP-ELEMENTARY-PROCEDURE ::= {
	INITIATING MESSAGE		MulticastGroupPaging
	PROCEDURE CODE			id-MulticastGroupPaging
	CRITICALITY				ignore
}


multicastContextSetup F1AP-ELEMENTARY-PROCEDURE ::= {
	INITIATING MESSAGE		MulticastContextSetupRequest
	SUCCESSFUL OUTCOME		MulticastContextSetupResponse
	UNSUCCESSFUL OUTCOME	MulticastContextSetupFailure
	PROCEDURE CODE			id-MulticastContextSetup
	CRITICALITY				reject
}

multicastContextRelease F1AP-ELEMENTARY-PROCEDURE ::= {
	INITIATING MESSAGE		MulticastContextReleaseCommand
	SUCCESSFUL OUTCOME		MulticastContextReleaseComplete
	PROCEDURE CODE			id-MulticastContextRelease
	CRITICALITY				reject
}

multicastContextReleaseRequest F1AP-ELEMENTARY-PROCEDURE ::= {
	INITIATING MESSAGE		MulticastContextReleaseRequest
	PROCEDURE CODE			id-MulticastContextReleaseRequest
	CRITICALITY				reject
}

multicastContextModification F1AP-ELEMENTARY-PROCEDURE ::= {
	INITIATING MESSAGE		MulticastContextModificationRequest
	SUCCESSFUL OUTCOME		MulticastContextModificationResponse
	UNSUCCESSFUL OUTCOME	MulticastContextModificationFailure
	PROCEDURE CODE			id-MulticastContextModification
	CRITICALITY				reject
}

multicastDistributionSetup F1AP-ELEMENTARY-PROCEDURE ::= {
	INITIATING MESSAGE		MulticastDistributionSetupRequest
	SUCCESSFUL OUTCOME		MulticastDistributionSetupResponse
	UNSUCCESSFUL OUTCOME	MulticastDistributionSetupFailure
	PROCEDURE CODE			id-MulticastDistributionSetup
	CRITICALITY				reject
}

multicastDistributionRelease F1AP-ELEMENTARY-PROCEDURE ::= {
	INITIATING MESSAGE		MulticastDistributionReleaseCommand
	SUCCESSFUL OUTCOME		MulticastDistributionReleaseComplete
	PROCEDURE CODE			id-MulticastDistributionRelease
	CRITICALITY				reject
}


pDCMeasurementInitiation F1AP-ELEMENTARY-PROCEDURE ::= {
	INITIATING MESSAGE		PDCMeasurementInitiationRequest
	SUCCESSFUL OUTCOME		PDCMeasurementInitiationResponse
	UNSUCCESSFUL OUTCOME	PDCMeasurementInitiationFailure
	PROCEDURE CODE			id-PDCMeasurementInitiation
	CRITICALITY				reject
}

pDCMeasurementReport F1AP-ELEMENTARY-PROCEDURE ::= {
	INITIATING MESSAGE		PDCMeasurementReport
	PROCEDURE CODE			id-PDCMeasurementReport
	CRITICALITY				ignore
}

pDCMeasurementTerminationCommand F1AP-ELEMENTARY-PROCEDURE ::= {
	INITIATING MESSAGE		PDCMeasurementTerminationCommand
	PROCEDURE CODE			id-PDCMeasurementTerminationCommand
	CRITICALITY				ignore
}

pDCMeasurementFailureIndication F1AP-ELEMENTARY-PROCEDURE ::= {
	INITIATING MESSAGE		PDCMeasurementFailureIndication
	PROCEDURE CODE			id-PDCMeasurementFailureIndication
	CRITICALITY				ignore
}

pRSConfigurationExchange F1AP-ELEMENTARY-PROCEDURE ::= {
	INITIATING MESSAGE		PRSConfigurationRequest
	SUCCESSFUL OUTCOME		PRSConfigurationResponse
	UNSUCCESSFUL OUTCOME	PRSConfigurationFailure
	PROCEDURE CODE			id-pRSConfigurationExchange
	CRITICALITY				reject
}

measurementPreconfiguration F1AP-ELEMENTARY-PROCEDURE ::= {
	INITIATING MESSAGE		MeasurementPreconfigurationRequired
	SUCCESSFUL OUTCOME		MeasurementPreconfigurationConfirm
	UNSUCCESSFUL OUTCOME	MeasurementPreconfigurationRefuse
	PROCEDURE CODE			id-measurementPreconfiguration
	CRITICALITY				reject
}


measurementActivation		F1AP-ELEMENTARY-PROCEDURE ::= {
	INITIATING MESSAGE		MeasurementActivation
	PROCEDURE CODE			id-measurementActivation
	CRITICALITY				ignore
}

qoEInformationTransfer F1AP-ELEMENTARY-PROCEDURE ::= {
	INITIATING MESSAGE		QoEInformationTransfer
	PROCEDURE CODE			id-QoEInformationTransfer
	CRITICALITY				ignore
}

posSystemInformationDelivery F1AP-ELEMENTARY-PROCEDURE ::= {
	INITIATING MESSAGE		PosSystemInformationDeliveryCommand
	PROCEDURE CODE			id-PosSystemInformationDeliveryCommand
	CRITICALITY				ignore
}


END

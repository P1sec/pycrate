-- ASN1START
-- **************************************************************
--
-- PDU definitions for XnAP.
--
-- **************************************************************

XnAP-PDU-Contents {
itu-t (0) identified-organization (4) etsi (0) mobileDomain (0)
ngran-access (22) modules (3) xnap (2) version1 (1) xnap-PDU-Contents (1) }

DEFINITIONS AUTOMATIC TAGS ::=

BEGIN

-- **************************************************************
--
-- IE parameter types from other modules.
--
-- **************************************************************

IMPORTS

	ActivationIDforCellActivation,
	AMF-Region-Information,
	AMF-UE-NGAP-ID,
	AS-SecurityInformation,
	AssistanceDataForRANPaging,
	BitRate,
	Cause,
	CellAndCapacityAssistanceInfo-EUTRA,
	CellAndCapacityAssistanceInfo-NR,
	CellAssistanceInfo-EUTRA,
	CellAssistanceInfo-NR,
	CHOinformation-Req,
	CHOinformation-Ack,
	CHOinformation-AddReq,
	CHOinformation-ModReq,
	CHO-MRDC-EarlyDataForwarding,
	CHO-MRDC-Indicator,
	CPTransportLayerInformation,
	TNLA-To-Add-List,
	TNLA-To-Update-List,
	TNLA-To-Remove-List,
	TNLA-Setup-List,
	TNLA-Failed-To-Setup-List,
	CriticalityDiagnostics,
	XnUAddressInfoperPDUSession-List,
	DAPSResponseInfo-List,
	DataTrafficResourceIndication,
	DeliveryStatus,
	DesiredActNotificationLevel,
	DRB-ID,
	DRB-List,
	DRB-Number,
	DRBsSubjectToDLDiscarding-List,
	DRBsSubjectToEarlyStatusTransfer-List,
	DRBsSubjectToStatusTransfer-List,
	DRBToQoSFlowMapping-List,
	E-UTRA-CGI,
	ExpectedUEActivityBehaviour,
	ExpectedUEBehaviour,
	ExtendedUEIdentityIndexValue,
	FiveGCMobilityRestrictionListContainer,
	GlobalCell-ID,
	GlobalNG-RANNode-ID,
	GlobalNG-RANCell-ID,
	GUAMI,
	InterfaceInstanceIndication,
	I-RNTI,
	Local-NG-RAN-Node-Identifier,
	LocationInformationSNReporting,
	LocationReportingInformation,
	LowerLayerPresenceStatusChange,
	LTEUESidelinkAggregateMaximumBitRate,
	LTEV2XServicesAuthorized,
	MR-DC-ResourceCoordinationInfo,
	ServedCells-E-UTRA,
	ServedCells-NR,
	ServedCellsToUpdate-E-UTRA,
	ServedCellsToUpdate-NR,
	MAC-I,
	MaskedIMEISV,
	MDT-Configuration,
	MDTPLMNList,
	MobilityRestrictionList,
	Neighbour-NG-RAN-Node-List,
	NG-RAN-Cell-Identity,
	NG-RANnodeUEXnAPID,
	NR-CGI,
	NE-DC-TDM-Pattern,
	NRUESidelinkAggregateMaximumBitRate,
	NRV2XServicesAuthorized,
	PagingDRX,
	EUTRAPagingeDRXInformation,
	PagingPriority,
	PartialListIndicator,
	PLMN-Identity,
	PDCPChangeIndication,
	PDUSessionAggregateMaximumBitRate,
	PDUSession-ID,
	PDUSession-List,
	PDUSession-List-withCause,
	PDUSession-List-withDataForwardingFromTarget,
	PDUSession-List-withDataForwardingRequest,
	PDUSessionResourcesAdmitted-List,
	PDUSessionResourcesNotAdmitted-List,
	PDUSessionResourcesToBeSetup-List,
	PDUSessionResourceChangeRequiredInfo-SNterminated,
	PDUSessionResourceChangeRequiredInfo-MNterminated,
	PDUSessionResourceChangeConfirmInfo-SNterminated,
	PDUSessionResourceChangeConfirmInfo-MNterminated,
	PDUSessionResourceSecondaryRATUsageList,
	PDUSessionResourceSetupInfo-SNterminated,
	PDUSessionResourceSetupInfo-MNterminated,
	PDUSessionResourceSetupResponseInfo-SNterminated,
	PDUSessionResourceSetupResponseInfo-MNterminated,
	PDUSessionResourceModificationInfo-SNterminated,
	PDUSessionResourceModificationInfo-MNterminated,
	PDUSessionResourceModificationResponseInfo-SNterminated,
	PDUSessionResourceModificationResponseInfo-MNterminated,
	PDUSessionResourceModConfirmInfo-SNterminated,
	PDUSessionResourceModConfirmInfo-MNterminated,
	PDUSessionResourceModRqdInfo-SNterminated,
	PDUSessionResourceModRqdInfo-MNterminated,
	PDUSessionType,
	PC5QoSParameters,
	QoSFlowIdentifier,
	QoSFlowNotificationControlIndicationInfo,
	QoSFlows-List,
	RANPagingArea,
	ResetRequestTypeInfo,
	ResetResponseTypeInfo,
	RFSP-Index,
	RRCConfigIndication,
	RRCResumeCause,
	SCGConfigurationQuery,
	SCGreconfigNotification,
	SecurityIndication,
	S-NG-RANnode-SecurityKey,
	SpectrumSharingGroupID,
	SplitSRBsTypes,
	S-NG-RANnode-Addition-Trigger-Ind,
	S-NSSAI,
	TargetCellList,
	TAISupport-List,
	Target-CGI,
	TimeToWait,
	TraceActivation,
	UEAggregateMaximumBitRate,
	UEContextID,
	UEContextInfoRetrUECtxtResp,
	UEContextKeptIndicator,
	UEHistoryInformation,
	UEIdentityIndexValue,
	UERadioCapabilityForPaging,
	UERadioCapabilityID,
	UERANPagingIdentity,
	UESecurityCapabilities,
	UPTransportLayerInformation,
	UserPlaneTrafficActivityReport,
	XnBenefitValue,
	RANPagingFailure,
	TNLConfigurationInfo,
	MaximumCellListSize,
	MessageOversizeNotification,
	NG-RANTraceID,
	MobilityInformation,
	InitiatingCondition-FailureIndication,
	HandoverReportType,
	TargetCellinEUTRAN,
	C-RNTI,
	UERLFReportContainer,
	Measurement-ID,
	RegistrationRequest,
	ReportCharacteristics,
	CellToReport,
	ReportingPeriodicity,
	CellMeasurementResult,
	UEHistoryInformationFromTheUE,
	MobilityParametersInformation,
	MobilityParametersModificationRange,
	RACHReportInformation,
	IABNodeIndication,
	SNTriggered,
	SCGIndicator,
	UESpecificDRX,
	DirectForwardingPathAvailability,
	TransportLayerAddress,
	PrivacyIndicator,
	URIaddress,
	MBS-Session-ID,
	UEIdentityIndexList-MBSGroupPaging,
	MBS-SessionInformation-List,
	MBS-SessionInformationResponse-List,
	SuccessfulHOReportInformation,
	PSCellHistoryInformationRetrieve,
	SSBOffsets-List,
	NG-RANnode2SSBOffsetsModificationRange,
	Coverage-Modification-List,
	SCGFailureReportContainer,
	SNMobilityInformation,
	PSCellChangeHistory,
	CHOConfiguration,
	SCGUEHistoryInformation,
	F1CTrafficContainer,
	NoPDUSessionIndication,
	IAB-TNL-Address-Request,
	IAB-TNL-Address-Response,
	TrafficIndex,
	TrafficProfile,
	TrafficToBeReleaseInformation,
	F1-TerminatingTopologyBHInformation,
	Non-F1-TerminatingTopologyBHInformation,
	BHInfoList,
	IABTNLAddress,
	IABCellInformation,
	IABTNLAddressException,
	TimeSynchronizationAssistanceInformation,
	SCGActivationRequest,
	SCGActivationStatus,
	CPAInformationRequest,
	CPAInformationAck,
	CPCInformationRequired,
	CPCInformationConfirm,
	CPAInformationModReq,
	CPAInformationModReqAck,
	CPC-DataForwarding-Indicator,
	CPCInformationUpdate,
	CPACInformationModRequired,
	QMCConfigInfo,
	FiveGProSeAuthorized,
	FiveGProSePC5QoSParameters,
	ServedCellSpecificInfoReq-NR,
	NRPagingeDRXInformation,
	NRPagingeDRXInformationforRRCINACTIVE,
	SDTSupportRequest,
	SDT-Termination-Request,
	SDTPartialUEContextInfo,
	SDTDataForwardingDRBList,
	PEIPSassistanceInformation,
	UESliceMaximumBitRateList,
	PagingCause,
	MDTPLMNModificationList,
	F1-terminatingIAB-donorIndicator,
	SRB-ID,
	AdditionalListofPDUSessionResourceChangeConfirmInfo-SNterminated


FROM XnAP-IEs

	PrivateIE-Container{},
	ProtocolExtensionContainer{},
	ProtocolIE-Container{},
	ProtocolIE-ContainerList{},
	ProtocolIE-ContainerPair{},
	ProtocolIE-ContainerPairList{},
	ProtocolIE-Single-Container{},
	XNAP-PRIVATE-IES,
	XNAP-PROTOCOL-EXTENSION,
	XNAP-PROTOCOL-IES,
	XNAP-PROTOCOL-IES-PAIR
FROM XnAP-Containers


	id-ActivatedServedCells,
	id-ActivationIDforCellActivation,
	id-AdditionalDRBIDs,
	id-AMF-Region-Information,
	id-AMF-Region-Information-To-Add,
	id-AMF-Region-Information-To-Delete,
	id-AssistanceDataForRANPaging,
	id-AvailableDRBIDs,
	id-Cause,
	id-cellAssistanceInfo-EUTRA,
	id-cellAssistanceInfo-NR,
	id-CellAndCapacityAssistanceInfo-EUTRA,
	id-CellAndCapacityAssistanceInfo-NR,
	id-ConfigurationUpdateInitiatingNodeChoice,
	id-UEContextID,
	id-CriticalityDiagnostics,
	id-XnUAddressInfoperPDUSession-List,
	id-DesiredActNotificationLevel,
	id-DRBsSubjectToStatusTransfer-List,
	id-ExpectedUEBehaviour,
	id-ExtendedUEIdentityIndexValue,
	id-FiveGCMobilityRestrictionListContainer,
	id-GlobalNG-RAN-node-ID,
	id-GUAMI,
	id-indexToRatFrequSelectionPriority,
	id-List-of-served-cells-E-UTRA,
	id-List-of-served-cells-NR,
	id-LocationInformationSN,
	id-LocationInformationSNReporting,
	id-LocationReportingInformation,
	id-LTEUESidelinkAggregateMaximumBitRate,
	id-LTEV2XServicesAuthorized,
	id-MAC-I,
	id-MaskedIMEISV,
	id-MDT-Configuration,
	id-MDTPLMNList,
	id-MN-to-SN-Container,
	id-MobilityRestrictionList,
	id-M-NG-RANnodeUEXnAPID,
	id-new-NG-RAN-Cell-Identity,
	id-newNG-RANnodeUEXnAPID,
	id-NRUESidelinkAggregateMaximumBitRate,
	id-NRV2XServicesAuthorized,
	id-oldNG-RANnodeUEXnAPID,
	id-OldtoNewNG-RANnodeResumeContainer,
	id-PagingCause,
	id-PagingDRX,
	id-EUTRAPagingeDRXInformation,
	id-PagingPriority,
	id-PartialListIndicator-EUTRA,
	id-PartialListIndicator-NR,
	id-PCellID,
	id-PDUSessionResourceSecondaryRATUsageList,
	id-PDUSessionResourcesActivityNotifyList,
	id-PDUSessionResourcesAdmitted-List,
	id-PDUSessionResourcesNotAdmitted-List,
	id-PDUSessionResourcesNotifyList,
	id-PDUSessionToBeAddedAddReq,
	id-PDUSessionToBeReleased-RelReqAck,
	id-procedureStage,
	id-RANPagingArea,
	id-requestedSplitSRB,
	id-RequiredNumberOfDRBIDs,
	id-ResetRequestTypeInfo,
	id-ResetResponseTypeInfo,
	id-RespondingNodeTypeConfigUpdateAck,
	id-RRCResumeCause,
	id-SCGreconfigNotification,
	id-selectedPLMN,
	id-ServedCellsToActivate,
	id-servedCellsToUpdate-E-UTRA,
	id-ServedCellsToUpdateInitiatingNodeChoice,
	id-servedCellsToUpdate-NR,
	id-sourceNG-RANnodeUEXnAPID,
	id-SpareDRBIDs,
	id-S-NG-RANnodeMaxIPDataRate-UL,
	id-S-NG-RANnodeMaxIPDataRate-DL,
	id-S-NG-RANnodeUEXnAPID,
	id-TAISupport-list,
	id-Target2SourceNG-RANnodeTranspContainer,
	id-targetCellGlobalID,
	id-targetNG-RANnodeUEXnAPID,
	id-TimeToWait,
	id-TNLA-To-Add-List,
	id-TNLA-To-Update-List,
	id-TNLA-To-Remove-List,
	id-TNLA-Setup-List,
	id-TNLA-Failed-To-Setup-List,
	id-TraceActivation,
	id-UEContextInfoHORequest,
	id-UEContextInfoRetrUECtxtResp,
	id-UEContextKeptIndicator,
	id-UEContextRefAtSN-HORequest,
	id-UEHistoryInformation,
	id-UEIdentityIndexValue,
	id-UERANPagingIdentity,
	id-UESecurityCapabilities,
	id-UserPlaneTrafficActivityReport,
	id-XnRemovalThreshold,
	id-PDUSessionAdmittedAddedAddReqAck,
	id-PDUSessionNotAdmittedAddReqAck,
	id-SN-to-MN-Container,
	id-RRCConfigIndication,
	id-SplitSRB-RRCTransfer,
	id-UEReportRRCTransfer,
	id-PDUSessionReleasedList-RelConf,
	id-BearersSubjectToCounterCheck,
	id-PDUSessionToBeReleasedList-RelRqd,
	id-ResponseInfo-ReconfCompl,
	id-initiatingNodeType-ResourceCoordRequest,
	id-respondingNodeType-ResourceCoordResponse,
	id-PDUSessionToBeReleased-RelReq,
	id-PDUSession-SNChangeRequired-List,
	id-PDUSession-SNChangeConfirm-List,
	id-PDCPChangeIndication,
	id-PC5QoSParameters,
	id-SCGConfigurationQuery,
	id-UEContextInfo-SNModRequest,
	id-requestedSplitSRBrelease,
	id-PDUSessionAdmitted-SNModResponse,
	id-PDUSessionNotAdmitted-SNModResponse,
	id-admittedSplitSRB,
	id-admittedSplitSRBrelease,
	id-PDUSessionAdmittedModSNModConfirm,
	id-PDUSessionReleasedSNModConfirm,
	id-s-ng-RANnode-SecurityKey,
	id-PDUSessionToBeModifiedSNModRequired,
	id-S-NG-RANnodeUE-AMBR,
	id-PDUSessionToBeReleasedSNModRequired,
	id-target-S-NG-RANnodeID,
	id-S-NSSAI,
	id-MR-DC-ResourceCoordinationInfo,
	id-RANPagingFailure,
	id-UERadioCapabilityForPaging,
	id-PDUSessionDataForwarding-SNModResponse,
	id-Secondary-MN-Xn-U-TNLInfoatM,
	id-NE-DC-TDM-Pattern,
	id-InterfaceInstanceIndication,
	id-S-NG-RANnode-Addition-Trigger-Ind,
	id-SNTriggered,
	id-DRBs-transferred-to-MN,
	id-TNLConfigurationInfo,
	id-MessageOversizeNotification,
	id-NG-RANTraceID,
	id-FastMCGRecoveryRRCTransfer-SN-to-MN,
	id-FastMCGRecoveryRRCTransfer-MN-to-SN,
	id-RequestedFastMCGRecoveryViaSRB3,
	id-AvailableFastMCGRecoveryViaSRB3,
	id-RequestedFastMCGRecoveryViaSRB3Release,
	id-ReleaseFastMCGRecoveryViaSRB3,
	id-CHOinformation-Req,
	id-CHOinformation-Ack,
	id-targetCellsToCancel,
	id-requestedTargetCellGlobalID,
	id-DAPSResponseInfo-List,
	id-CHO-MRDC-EarlyDataForwarding,
	id-CHO-MRDC-Indicator,
	id-MobilityInformation,
	id-InitiatingCondition-FailureIndication,
	id-UEHistoryInformationFromTheUE,
	id-HandoverReportType,
	id-HandoverCause,
	id-SourceCellCGI,
	id-TargetCellCGI,
	id-ReEstablishmentCellCGI,
	id-TargetCellinEUTRAN,
	id-SourceCellCRNTI,
	id-UERLFReportContainer,
	id-NGRAN-Node1-Measurement-ID,
	id-NGRAN-Node2-Measurement-ID,
	id-RegistrationRequest,
	id-ReportCharacteristics,
	id-CellToReport,
	id-ReportingPeriodicity,
	id-CellMeasurementResult,
	id-NG-RANnode1CellID,
	id-NG-RANnode2CellID,
	id-NG-RANnode1MobilityParameters,
	id-NG-RANnode2ProposedMobilityParameters,
	id-MobilityParametersModificationRange,
	id-RACHReportInformation,
	id-IABNodeIndication,
	id-UERadioCapabilityID,
	id-SCGIndicator,
	id-UESpecificDRX,
	id-PDUSessionExpectedUEActivityBehaviour,
	id-DirectForwardingPathAvailability,
	id-SourceNG-RAN-node-ID,
	id-TargetNodeID,
	id-ManagementBasedMDTPLMNList,
	id-PrivacyIndicator,
	id-TraceCollectionEntityIPAddress,
	id-TraceCollectionEntityURI,
	id-MBS-Session-ID,
	id-UEIdentityIndexList-MBSGroupPaging,
	id-MulticastRANPagingArea,
	id-MBS-SessionInformation-List,
	id-MBS-SessionInformationResponse-List,
	id-SuccessfulHOReportInformation,
	id-PSCellHistoryInformationRetrieve,
	id-SSBOffsets-List,
	id-NG-RANnode2SSBOffsetsModificationRange,
	id-Coverage-Modification-List,
	id-SourcePSCellCGI,
	id-FailedPSCellCGI,
	id-SCGFailureReportContainer,
	id-SNMobilityInformation,
	id-SourcePSCellID,
	id-SuitablePSCellCGI,
	id-PSCellChangeHistory,
	id-CHOConfiguration,
	id-SCGUEHistoryInformation,
	id-F1CTrafficContainer,
	id-NoPDUSessionIndication,
	id-F1-Terminating-IAB-DonorUEXnAPID,
	id-nonF1-Terminating-IAB-DonorUEXnAPID,
	id-IAB-TNL-Address-Request,
	id-IAB-TNL-Address-Response,
	id-TrafficToBeAddedList,
	id-TrafficToBeModifiedList,
	id-TrafficToBeReleaseInformation,
	id-TrafficAddedList,
	id-TrafficModifiedList,
	id-TrafficNotAddedList,
	id-TrafficNotModifiedList,
	id-TrafficRequiredToBeModifiedList,
	id-TrafficRequiredModifiedList,
	id-TrafficReleasedList,
	id-IABTNLAddressToBeAdded,
	id-IABTNLAddressToBeReleasedList,
	id-BoundaryNodeCellsList,
	id-ParentNodeCellsList,
	id-IABTNLAddressException,
	id-CHOinformation-AddReq,
	id-CHOinformation-ModReq,
	id-TimeSynchronizationAssistanceInformation,
	id-SCGActivationRequest,
	id-SCGActivationStatus,
	id-CPAInformationRequest,
	id-CPAInformationAck,
	id-CPCInformationRequired,
	id-CPCInformationConfirm,
	id-CPAInformationModReq,
	id-CPAInformationModReqAck,
	id-CPC-DataForwarding-Indicator,
	id-CPCInformationUpdate,
	id-CPACInformationModRequired,
	id-QMCConfigInfo,
	id-Local-NG-RAN-Node-Identifier,
	id-Neighbour-NG-RAN-Node-List,
	id-Local-NG-RAN-Node-Identifier-Removal,
	id-FiveGProSeAuthorized,
	id-FiveGProSePC5QoSParameters,
	id-FiveGProSeUEPC5AggregateMaximumBitRate,
	id-ServedCellSpecificInfoReq-NR,
	id-NRPagingeDRXInformation,
	id-NRPagingeDRXInformationforRRCINACTIVE,
	id-SDTSupportRequest,
	id-SDT-SRB-between-NewNode-OldNode,
	id-SDT-Termination-Request,
	id-SDTPartialUEContextInfo,
	id-SDTDataForwardingDRBList,
	id-PEIPSassistanceInformation,
	id-UESliceMaximumBitRateList,
	id-S-NG-RANnodeUE-Slice-MBR,
	id-ManagementBasedMDTPLMNModificationList,
	id-F1-terminatingIAB-donorIndicator,
	id-AdditionalListofPDUSessionResourceChangeConfirmInfo-SNterminated,



	maxnoofCellsinNG-RANnode,
	maxnoofDRBs,
	maxnoofPDUSessions,
	maxnoofQoSFlows,
	maxnoofServedCellsIAB,
	maxnoofTrafficIndexEntries,
	maxnoofTLAsIAB,
	maxnoofBAPControlPDURLCCHs,
	maxnoofServingCells

FROM XnAP-Constants;

-- **************************************************************
--
-- HANDOVER REQUEST
--
-- **************************************************************

HandoverRequest ::= SEQUENCE {
	protocolIEs			ProtocolIE-Container	{{HandoverRequest-IEs}},
	...
}

HandoverRequest-IEs XNAP-PROTOCOL-IES ::= {
	{ ID id-sourceNG-RANnodeUEXnAPID			CRITICALITY reject	TYPE NG-RANnodeUEXnAPID							PRESENCE mandatory}|
	{ ID id-Cause								CRITICALITY reject	TYPE Cause										PRESENCE mandatory}|
	{ ID id-targetCellGlobalID					CRITICALITY reject	TYPE Target-CGI									PRESENCE mandatory}|
	{ ID id-GUAMI								CRITICALITY reject	TYPE GUAMI										PRESENCE mandatory}|
	{ ID id-UEContextInfoHORequest				CRITICALITY reject	TYPE UEContextInfoHORequest						PRESENCE mandatory}|
	{ ID id-TraceActivation						CRITICALITY ignore	TYPE TraceActivation							PRESENCE optional }|
	{ ID id-MaskedIMEISV						CRITICALITY ignore	TYPE MaskedIMEISV								PRESENCE optional }|
	{ ID id-UEHistoryInformation				CRITICALITY ignore	TYPE UEHistoryInformation						PRESENCE mandatory}|
	{ ID id-UEContextRefAtSN-HORequest			CRITICALITY ignore	TYPE UEContextRefAtSN-HORequest				PRESENCE optional }|
	{ ID id-CHOinformation-Req					CRITICALITY reject	TYPE CHOinformation-Req							PRESENCE optional }|
	{ ID id-NRV2XServicesAuthorized				CRITICALITY ignore	TYPE NRV2XServicesAuthorized					PRESENCE optional }|
	{ ID id-LTEV2XServicesAuthorized			CRITICALITY ignore	TYPE LTEV2XServicesAuthorized					PRESENCE optional }|
	{ ID id-PC5QoSParameters					CRITICALITY ignore	TYPE PC5QoSParameters							PRESENCE optional }|
	{ ID id-MobilityInformation					CRITICALITY ignore	TYPE MobilityInformation						PRESENCE optional }|
	{ ID id-UEHistoryInformationFromTheUE		CRITICALITY ignore	TYPE UEHistoryInformationFromTheUE			PRESENCE optional }|
	{ ID id-IABNodeIndication					CRITICALITY reject	TYPE IABNodeIndication							PRESENCE optional }|
	{ ID id-NoPDUSessionIndication				CRITICALITY ignore	TYPE NoPDUSessionIndication						PRESENCE optional }|
	{ ID id-TimeSynchronizationAssistanceInformation	CRITICALITY ignore	TYPE TimeSynchronizationAssistanceInformation		PRESENCE optional }|
	{ ID id-QMCConfigInfo						CRITICALITY ignore	TYPE QMCConfigInfo								PRESENCE optional }|
	{ ID id-FiveGProSeAuthorized				CRITICALITY ignore	TYPE FiveGProSeAuthorized						PRESENCE optional }|
	{ ID id-FiveGProSePC5QoSParameters			CRITICALITY ignore	TYPE FiveGProSePC5QoSParameters				PRESENCE optional },
	...
}

UEContextInfoHORequest ::= SEQUENCE {
	ng-c-UE-reference						AMF-UE-NGAP-ID,
	cp-TNL-info-source						CPTransportLayerInformation,
	ueSecurityCapabilities					UESecurityCapabilities,
	securityInformation						AS-SecurityInformation,
	indexToRatFrequencySelectionPriority	RFSP-Index															OPTIONAL,
	ue-AMBR									UEAggregateMaximumBitRate,
	pduSessionResourcesToBeSetup-List		PDUSessionResourcesToBeSetup-List,
	rrc-Context								OCTET STRING,
	locationReportingInformation			LocationReportingInformation										OPTIONAL,
	mrl										MobilityRestrictionList												OPTIONAL,
	iE-Extensions							ProtocolExtensionContainer { {UEContextInfoHORequest-ExtIEs} }	OPTIONAL,
	...
}

UEContextInfoHORequest-ExtIEs XNAP-PROTOCOL-EXTENSION ::={
	{ ID id-FiveGCMobilityRestrictionListContainer	CRITICALITY ignore	EXTENSION FiveGCMobilityRestrictionListContainer		PRESENCE optional }|
	{ ID id-NRUESidelinkAggregateMaximumBitRate		CRITICALITY ignore	EXTENSION NRUESidelinkAggregateMaximumBitRate			PRESENCE optional }|
	{ ID id-LTEUESidelinkAggregateMaximumBitRate	CRITICALITY ignore	EXTENSION LTEUESidelinkAggregateMaximumBitRate			PRESENCE optional }|
	{ ID id-MDTPLMNList								CRITICALITY ignore	EXTENSION MDTPLMNList											PRESENCE optional }|
	{ ID id-UERadioCapabilityID						CRITICALITY reject	EXTENSION UERadioCapabilityID								PRESENCE optional }|
	{ ID id-MBS-SessionInformation-List				CRITICALITY ignore	EXTENSION MBS-SessionInformation-List						PRESENCE optional }|
	{ ID id-FiveGProSeUEPC5AggregateMaximumBitRate	CRITICALITY ignore	EXTENSION NRUESidelinkAggregateMaximumBitRate			PRESENCE optional }|
	{ ID id-UESliceMaximumBitRateList				CRITICALITY ignore	EXTENSION UESliceMaximumBitRateList						PRESENCE optional },
	...
}

UEContextRefAtSN-HORequest ::= SEQUENCE {
	globalNG-RANNode-ID				GlobalNG-RANNode-ID,
	sN-NG-RANnodeUEXnAPID			NG-RANnodeUEXnAPID,
	iE-Extensions					ProtocolExtensionContainer { {UEContextRefAtSN-HORequest-ExtIEs} }	OPTIONAL,
	...
}

UEContextRefAtSN-HORequest-ExtIEs XNAP-PROTOCOL-EXTENSION ::={
	...
}

-- **************************************************************
--
-- HANDOVER REQUEST ACKNOWLEDGE
--
-- **************************************************************

HandoverRequestAcknowledge ::= SEQUENCE {
	protocolIEs			ProtocolIE-Container	{{HandoverRequestAcknowledge-IEs}},
	...
}

HandoverRequestAcknowledge-IEs XNAP-PROTOCOL-IES ::= {
	{ ID id-sourceNG-RANnodeUEXnAPID				CRITICALITY ignore	TYPE NG-RANnodeUEXnAPID								PRESENCE mandatory}|
	{ ID id-targetNG-RANnodeUEXnAPID				CRITICALITY ignore	TYPE NG-RANnodeUEXnAPID								PRESENCE mandatory}|
	{ ID id-PDUSessionResourcesAdmitted-List		CRITICALITY ignore	TYPE PDUSessionResourcesAdmitted-List			PRESENCE mandatory}|
	{ ID id-PDUSessionResourcesNotAdmitted-List		CRITICALITY ignore	TYPE PDUSessionResourcesNotAdmitted-List		PRESENCE optional }|
	{ ID id-Target2SourceNG-RANnodeTranspContainer	CRITICALITY ignore	TYPE OCTET STRING									PRESENCE mandatory}|
	{ ID id-UEContextKeptIndicator					CRITICALITY ignore	TYPE UEContextKeptIndicator						PRESENCE optional }|
	{ ID id-CriticalityDiagnostics					CRITICALITY ignore	TYPE CriticalityDiagnostics						PRESENCE optional }|
	{ ID id-DRBs-transferred-to-MN					CRITICALITY ignore	TYPE DRB-List										PRESENCE optional }|
	{ ID id-DAPSResponseInfo-List					CRITICALITY reject	TYPE DAPSResponseInfo-List						PRESENCE optional }|
	{ ID id-CHOinformation-Ack						CRITICALITY reject	TYPE CHOinformation-Ack								PRESENCE optional }|
	{ ID id-MBS-SessionInformationResponse-List		CRITICALITY ignore	TYPE MBS-SessionInformationResponse-List		PRESENCE optional },
	...
}

-- **************************************************************
--
-- HANDOVER PREPARATION FAILURE
--
-- **************************************************************

HandoverPreparationFailure ::= SEQUENCE {
	protocolIEs			ProtocolIE-Container	{{HandoverPreparationFailure-IEs}},
	...
}

HandoverPreparationFailure-IEs XNAP-PROTOCOL-IES ::= {
	{ ID id-sourceNG-RANnodeUEXnAPID				CRITICALITY ignore	TYPE NG-RANnodeUEXnAPID							PRESENCE mandatory}|
	{ ID id-Cause									CRITICALITY ignore	TYPE Cause										PRESENCE mandatory}|
	{ ID id-CriticalityDiagnostics					CRITICALITY ignore	TYPE CriticalityDiagnostics					PRESENCE optional }|
	{ ID id-requestedTargetCellGlobalID				CRITICALITY reject	TYPE Target-CGI									PRESENCE optional},
	...
}

-- **************************************************************
--
-- SN STATUS TRANSFER
--
-- **************************************************************

SNStatusTransfer ::= SEQUENCE {
	protocolIEs			ProtocolIE-Container	{{SNStatusTransfer-IEs}},
	...
}

SNStatusTransfer-IEs XNAP-PROTOCOL-IES ::= {
	{ ID id-sourceNG-RANnodeUEXnAPID				CRITICALITY reject		TYPE NG-RANnodeUEXnAPID							PRESENCE mandatory}|
	{ ID id-targetNG-RANnodeUEXnAPID				CRITICALITY reject		TYPE NG-RANnodeUEXnAPID							PRESENCE mandatory}|
	{ ID id-DRBsSubjectToStatusTransfer-List		CRITICALITY ignore		TYPE DRBsSubjectToStatusTransfer-List		PRESENCE mandatory}|
	{ ID id-CHOConfiguration							CRITICALITY ignore		TYPE CHOConfiguration								PRESENCE optional}|
	{ ID id-MobilityInformation						CRITICALITY ignore		TYPE MobilityInformation							PRESENCE optional},
	...
}

-- **************************************************************
--
-- UE CONTEXT RELEASE
--
-- **************************************************************

UEContextRelease ::= SEQUENCE {
	protocolIEs			ProtocolIE-Container	{{UEContextRelease-IEs}},
	...
}

UEContextRelease-IEs XNAP-PROTOCOL-IES ::= {
	{ ID id-sourceNG-RANnodeUEXnAPID					CRITICALITY reject		TYPE NG-RANnodeUEXnAPID							PRESENCE mandatory}|
	{ ID id-targetNG-RANnodeUEXnAPID					CRITICALITY reject		TYPE NG-RANnodeUEXnAPID							PRESENCE mandatory},
	...
}

-- **************************************************************
--
-- HANDOVER CANCEL
--
-- **************************************************************

HandoverCancel ::= SEQUENCE {
	protocolIEs			ProtocolIE-Container	{{HandoverCancel-IEs}},
	...
}

HandoverCancel-IEs XNAP-PROTOCOL-IES ::= {
	{ ID id-sourceNG-RANnodeUEXnAPID					CRITICALITY reject		TYPE NG-RANnodeUEXnAPID							PRESENCE mandatory}|
	{ ID id-targetNG-RANnodeUEXnAPID					CRITICALITY ignore		TYPE NG-RANnodeUEXnAPID							PRESENCE optional }|
	{ ID id-Cause										CRITICALITY ignore		TYPE Cause											PRESENCE mandatory}|
	{ ID id-targetCellsToCancel							CRITICALITY reject		TYPE TargetCellList								PRESENCE optional},
	...
}

-- **************************************************************
--
-- HANDOVER SUCCESS
--
-- **************************************************************

HandoverSuccess ::= SEQUENCE {
	protocolIEs			ProtocolIE-Container	{{HandoverSuccess-IEs}},
	...
}

HandoverSuccess-IEs XNAP-PROTOCOL-IES ::= {
	{ ID id-sourceNG-RANnodeUEXnAPID					CRITICALITY reject		TYPE NG-RANnodeUEXnAPID							PRESENCE mandatory}|
	{ ID id-targetNG-RANnodeUEXnAPID					CRITICALITY reject		TYPE NG-RANnodeUEXnAPID							PRESENCE mandatory}|
	{ ID id-requestedTargetCellGlobalID					CRITICALITY reject		TYPE Target-CGI										PRESENCE mandatory},
	...
}

-- **************************************************************
--
-- CONDITIONAL HANDOVER CANCEL
--
-- **************************************************************

ConditionalHandoverCancel ::= SEQUENCE {
	protocolIEs			ProtocolIE-Container	{{ ConditionalHandoverCancel-IEs}},
	...
}

ConditionalHandoverCancel-IEs XNAP-PROTOCOL-IES ::= {
	{ ID id-sourceNG-RANnodeUEXnAPID					CRITICALITY reject		TYPE NG-RANnodeUEXnAPID							PRESENCE mandatory}|
	{ ID id-targetNG-RANnodeUEXnAPID					CRITICALITY reject		TYPE NG-RANnodeUEXnAPID							PRESENCE mandatory}|
	{ ID id-Cause										CRITICALITY ignore		TYPE Cause											PRESENCE mandatory}|
	{ ID id-targetCellsToCancel							CRITICALITY reject		TYPE TargetCellList								PRESENCE optional},
	...
}

-- **************************************************************
--
-- EARLY STATUS TRANSFER
--
-- **************************************************************

EarlyStatusTransfer ::= SEQUENCE {
	protocolIEs			ProtocolIE-Container	{{ EarlyStatusTransfer-IEs}},
	...
}

EarlyStatusTransfer-IEs XNAP-PROTOCOL-IES ::= {
	{ ID id-sourceNG-RANnodeUEXnAPID					CRITICALITY reject		TYPE NG-RANnodeUEXnAPID							PRESENCE mandatory}|
	{ ID id-targetNG-RANnodeUEXnAPID					CRITICALITY reject		TYPE NG-RANnodeUEXnAPID							PRESENCE mandatory}|
	{ ID id-procedureStage								CRITICALITY reject		TYPE ProcedureStageChoice						PRESENCE mandatory},
	...
}

ProcedureStageChoice ::= CHOICE {
	first-dl-count						FirstDLCount,
	dl-discarding						DLDiscarding,
	choice-extension					ProtocolIE-Single-Container { {ProcedureStageChoice-ExtIEs} }
}

ProcedureStageChoice-ExtIEs XNAP-PROTOCOL-IES ::= {
	...
}

FirstDLCount ::= SEQUENCE {
	dRBsSubjectToEarlyStatusTransfer			DRBsSubjectToEarlyStatusTransfer-List,
	iE-Extension								ProtocolExtensionContainer { {FirstDLCount-ExtIEs} }	OPTIONAL,
	...
}

FirstDLCount-ExtIEs XNAP-PROTOCOL-EXTENSION ::= {
	...
}

DLDiscarding ::= SEQUENCE {
	dRBsSubjectToDLDiscarding					DRBsSubjectToDLDiscarding-List,
	iE-Extension								ProtocolExtensionContainer { {DLDiscarding-ExtIEs} }	OPTIONAL,
	...
}

DLDiscarding-ExtIEs XNAP-PROTOCOL-EXTENSION ::= {
	...
}

-- **************************************************************
--
-- RAN PAGING
--
-- **************************************************************

RANPaging ::= SEQUENCE {
	protocolIEs			ProtocolIE-Container	{{RANPaging-IEs}},
	...
}

RANPaging-IEs XNAP-PROTOCOL-IES ::= {
	{ ID id-UEIdentityIndexValue					CRITICALITY reject		TYPE UEIdentityIndexValue						PRESENCE mandatory}|
	{ ID id-UERANPagingIdentity						CRITICALITY ignore		TYPE UERANPagingIdentity							PRESENCE mandatory}|
	{ ID id-PagingDRX								CRITICALITY ignore		TYPE PagingDRX										PRESENCE mandatory}|
	{ ID id-RANPagingArea							CRITICALITY reject		TYPE RANPagingArea									PRESENCE mandatory}|
	{ ID id-PagingPriority							CRITICALITY ignore		TYPE PagingPriority									PRESENCE optional }|
	{ ID id-AssistanceDataForRANPaging				CRITICALITY ignore		TYPE AssistanceDataForRANPaging				PRESENCE optional }|
	{ ID id-UERadioCapabilityForPaging				CRITICALITY ignore		TYPE UERadioCapabilityForPaging				PRESENCE optional }|
	{ ID id-ExtendedUEIdentityIndexValue			CRITICALITY ignore		TYPE ExtendedUEIdentityIndexValue				PRESENCE optional }|
	{ ID id-EUTRAPagingeDRXInformation				CRITICALITY ignore		TYPE EUTRAPagingeDRXInformation				PRESENCE optional }|
	{ ID id-UESpecificDRX							CRITICALITY ignore		TYPE UESpecificDRX									PRESENCE optional }|
	{ ID id-NRPagingeDRXInformation					CRITICALITY ignore		TYPE NRPagingeDRXInformation					PRESENCE optional }|
	{ ID id-NRPagingeDRXInformationforRRCINACTIVE	CRITICALITY ignore		TYPE NRPagingeDRXInformationforRRCINACTIVE	PRESENCE optional }|
	{ ID id-PagingCause								CRITICALITY ignore		TYPE PagingCause										PRESENCE optional }|
	{ ID id-PEIPSassistanceInformation				CRITICALITY ignore		TYPE PEIPSassistanceInformation				PRESENCE optional },
	...
}

-- **************************************************************
--
-- RETRIEVE UE CONTEXT REQUEST
--
-- **************************************************************

RetrieveUEContextRequest ::= SEQUENCE {
	protocolIEs			ProtocolIE-Container	{{RetrieveUEContextRequest-IEs}},
	...
}

RetrieveUEContextRequest-IEs XNAP-PROTOCOL-IES ::= {
	{ ID id-newNG-RANnodeUEXnAPID					CRITICALITY reject		TYPE NG-RANnodeUEXnAPID							PRESENCE mandatory}|
	{ ID id-UEContextID								CRITICALITY reject		TYPE UEContextID									PRESENCE mandatory}|
	{ ID id-MAC-I									CRITICALITY reject		TYPE MAC-I											PRESENCE mandatory}|
	{ ID id-new-NG-RAN-Cell-Identity				CRITICALITY reject		TYPE NG-RAN-Cell-Identity						PRESENCE mandatory}|
	{ ID id-RRCResumeCause							CRITICALITY ignore		TYPE RRCResumeCause									PRESENCE optional }|
	{ ID id-SDTSupportRequest						CRITICALITY ignore		TYPE SDTSupportRequest							PRESENCE optional },
	...
}

-- **************************************************************
--
-- RETRIEVE UE CONTEXT RESPONSE
--
-- **************************************************************

RetrieveUEContextResponse ::= SEQUENCE {
	protocolIEs			ProtocolIE-Container	{{ RetrieveUEContextResponse-IEs}},
	...
}

RetrieveUEContextResponse-IEs XNAP-PROTOCOL-IES ::= {
	{ ID id-newNG-RANnodeUEXnAPID						CRITICALITY ignore	TYPE NG-RANnodeUEXnAPID									PRESENCE mandatory}|
	{ ID id-oldNG-RANnodeUEXnAPID						CRITICALITY ignore	TYPE NG-RANnodeUEXnAPID									PRESENCE mandatory}|
	{ ID id-GUAMI										CRITICALITY reject	TYPE GUAMI													PRESENCE mandatory}|
	{ ID id-UEContextInfoRetrUECtxtResp					CRITICALITY reject	TYPE UEContextInfoRetrUECtxtResp						PRESENCE mandatory}|
	{ ID id-TraceActivation								CRITICALITY ignore	TYPE TraceActivation										PRESENCE optional }|
	{ ID id-MaskedIMEISV								CRITICALITY ignore	TYPE MaskedIMEISV											PRESENCE optional }|
	{ ID id-LocationReportingInformation				CRITICALITY ignore	TYPE LocationReportingInformation						PRESENCE optional }|
	{ ID id-CriticalityDiagnostics						CRITICALITY ignore	TYPE CriticalityDiagnostics								PRESENCE optional }|
	{ ID id-NRV2XServicesAuthorized						CRITICALITY ignore	TYPE NRV2XServicesAuthorized							PRESENCE optional }|
	{ ID id-LTEV2XServicesAuthorized					CRITICALITY ignore	TYPE LTEV2XServicesAuthorized							PRESENCE optional }|
	{ ID id-PC5QoSParameters							CRITICALITY ignore	TYPE PC5QoSParameters										PRESENCE optional }|
	{ ID id-UEHistoryInformation						CRITICALITY ignore	TYPE UEHistoryInformation								PRESENCE optional }|
	{ ID id-UEHistoryInformationFromTheUE				CRITICALITY ignore	TYPE UEHistoryInformationFromTheUE					PRESENCE optional }|
	{ ID id-MDTPLMNList									CRITICALITY ignore	TYPE MDTPLMNList											PRESENCE optional }|
	{ ID id-IABNodeIndication							CRITICALITY reject	TYPE IABNodeIndication									PRESENCE optional }|
	{ ID id-UEContextRefAtSN-HORequest					CRITICALITY ignore	TYPE UEContextRefAtSN-HORequest						PRESENCE optional }|
	{ ID id-TimeSynchronizationAssistanceInformation	CRITICALITY ignore	TYPE TimeSynchronizationAssistanceInformation		PRESENCE optional }|
	{ ID id-QMCConfigInfo								CRITICALITY ignore	TYPE QMCConfigInfo											PRESENCE optional }|
	{ ID id-FiveGProSeAuthorized						CRITICALITY ignore	TYPE FiveGProSeAuthorized								PRESENCE optional }|
	{ ID id-FiveGProSePC5QoSParameters					CRITICALITY ignore	TYPE FiveGProSePC5QoSParameters						PRESENCE optional },
	...
}

-- **************************************************************
--
-- RETRIEVE UE CONTEXT CONFIRM
--
-- **************************************************************

RetrieveUEContextConfirm ::= SEQUENCE {
	protocolIEs			ProtocolIE-Container	{{RetrieveUEContextConfirm-IEs}},
	...
}
RetrieveUEContextConfirm-IEs XNAP-PROTOCOL-IES ::= {
	{ ID id-oldNG-RANnodeUEXnAPID					CRITICALITY ignore		TYPE NG-RANnodeUEXnAPID							PRESENCE mandatory}|
	{ ID id-newNG-RANnodeUEXnAPID					CRITICALITY ignore		TYPE NG-RANnodeUEXnAPID							PRESENCE mandatory}|
	{ ID id-UEContextKeptIndicator					CRITICALITY ignore		TYPE UEContextKeptIndicator						PRESENCE optional }|
	{ ID id-SDT-Termination-Request					CRITICALITY ignore		TYPE SDT-Termination-Request					PRESENCE optional },
	...
}



-- **************************************************************
--
-- RETRIEVE UE CONTEXT FAILURE
--
-- **************************************************************

RetrieveUEContextFailure ::= SEQUENCE {
	protocolIEs			ProtocolIE-Container	{{ RetrieveUEContextFailure-IEs}},
	...
}

RetrieveUEContextFailure-IEs XNAP-PROTOCOL-IES ::= {
	{ ID id-newNG-RANnodeUEXnAPID					CRITICALITY ignore		TYPE NG-RANnodeUEXnAPID							PRESENCE mandatory}|
	{ ID id-OldtoNewNG-RANnodeResumeContainer		CRITICALITY ignore		TYPE OCTET STRING									PRESENCE optional }|
	{ ID id-Cause									CRITICALITY ignore		TYPE Cause											PRESENCE mandatory}|
	{ ID id-CriticalityDiagnostics					CRITICALITY ignore		TYPE CriticalityDiagnostics						PRESENCE optional },
	...
}

-- **************************************************************
--
-- XN-U ADDRESS INDICATION
--
-- **************************************************************

XnUAddressIndication ::= SEQUENCE {
	protocolIEs			ProtocolIE-Container	{{ XnUAddressIndication-IEs}},
	...
}

XnUAddressIndication-IEs XNAP-PROTOCOL-IES ::= {
	{ ID id-newNG-RANnodeUEXnAPID					CRITICALITY ignore		TYPE NG-RANnodeUEXnAPID							PRESENCE mandatory}|
	{ ID id-oldNG-RANnodeUEXnAPID					CRITICALITY ignore		TYPE NG-RANnodeUEXnAPID							PRESENCE mandatory}|
	{ ID id-XnUAddressInfoperPDUSession-List		CRITICALITY reject		TYPE XnUAddressInfoperPDUSession-List		PRESENCE mandatory}|
	{ ID id-CHO-MRDC-Indicator						CRITICALITY reject		TYPE CHO-MRDC-Indicator							PRESENCE optional }|
	{ ID id-CHO-MRDC-EarlyDataForwarding			CRITICALITY ignore		TYPE CHO-MRDC-EarlyDataForwarding				PRESENCE optional }|
	{ ID id-CPC-DataForwarding-Indicator			CRITICALITY reject		TYPE CPC-DataForwarding-Indicator				PRESENCE optional },
	...
}

-- **************************************************************
--
-- S-NODE ADDITION REQUEST
--
-- **************************************************************

SNodeAdditionRequest ::= SEQUENCE {
	protocolIEs			ProtocolIE-Container	{{ SNodeAdditionRequest-IEs}},
	...
}

SNodeAdditionRequest-IEs XNAP-PROTOCOL-IES ::= {
	{ ID id-M-NG-RANnodeUEXnAPID				CRITICALITY reject		TYPE NG-RANnodeUEXnAPID								PRESENCE mandatory}|
	{ ID id-UESecurityCapabilities				CRITICALITY reject		TYPE UESecurityCapabilities						PRESENCE mandatory}|
	{ ID id-s-ng-RANnode-SecurityKey			CRITICALITY reject		TYPE S-NG-RANnode-SecurityKey					PRESENCE mandatory}|
	{ ID id-S-NG-RANnodeUE-AMBR					CRITICALITY reject		TYPE UEAggregateMaximumBitRate					PRESENCE mandatory}|
	{ ID id-selectedPLMN						CRITICALITY ignore		TYPE PLMN-Identity									PRESENCE optional }|
	{ ID id-MobilityRestrictionList				CRITICALITY ignore		TYPE MobilityRestrictionList						PRESENCE optional }|
	{ ID id-indexToRatFrequSelectionPriority	CRITICALITY reject		TYPE RFSP-Index										PRESENCE optional }|
	{ ID id-PDUSessionToBeAddedAddReq			CRITICALITY reject		TYPE PDUSessionToBeAddedAddReq					PRESENCE mandatory}|
	{ ID id-MN-to-SN-Container					CRITICALITY reject		TYPE OCTET STRING									PRESENCE mandatory}|
	{ ID id-S-NG-RANnodeUEXnAPID				CRITICALITY reject		TYPE NG-RANnodeUEXnAPID								PRESENCE optional }|
	{ ID id-ExpectedUEBehaviour					CRITICALITY ignore		TYPE ExpectedUEBehaviour							PRESENCE optional }|
	{ ID id-requestedSplitSRB					CRITICALITY reject		TYPE SplitSRBsTypes									PRESENCE optional }|
	{ ID id-PCellID								CRITICALITY reject		TYPE GlobalNG-RANCell-ID							PRESENCE optional }|
	{ ID id-DesiredActNotificationLevel			CRITICALITY ignore		TYPE DesiredActNotificationLevel				PRESENCE optional }|
	{ ID id-AvailableDRBIDs						CRITICALITY reject		TYPE DRB-List										PRESENCE conditional}
 -- The IE shall be present if there is at least one  PDUSessionResourceSetupInfo-SNterminated included --|
	{ ID id-S-NG-RANnodeMaxIPDataRate-UL		CRITICALITY reject		TYPE BitRate										PRESENCE optional }|
	{ ID id-S-NG-RANnodeMaxIPDataRate-DL		CRITICALITY reject		TYPE BitRate										PRESENCE optional }|
	{ ID id-LocationInformationSNReporting		CRITICALITY ignore		TYPE LocationInformationSNReporting			PRESENCE optional }|
	{ ID id-MR-DC-ResourceCoordinationInfo		CRITICALITY ignore		TYPE MR-DC-ResourceCoordinationInfo			PRESENCE optional }|
	{ ID id-MaskedIMEISV						CRITICALITY ignore		TYPE MaskedIMEISV									PRESENCE optional }|
	{ ID id-NE-DC-TDM-Pattern					CRITICALITY ignore		TYPE NE-DC-TDM-Pattern								PRESENCE optional }|
	{ ID id-S-NG-RANnode-Addition-Trigger-Ind	CRITICALITY reject		TYPE S-NG-RANnode-Addition-Trigger-Ind		PRESENCE optional }|
	{ ID id-TraceActivation						CRITICALITY ignore		TYPE TraceActivation								PRESENCE optional }|
	{ ID id-RequestedFastMCGRecoveryViaSRB3		CRITICALITY ignore		TYPE RequestedFastMCGRecoveryViaSRB3			PRESENCE optional }|
	{ ID id-UERadioCapabilityID					CRITICALITY reject		TYPE UERadioCapabilityID							PRESENCE optional }|
	{ ID id-SourceNG-RAN-node-ID				CRITICALITY ignore		TYPE GlobalNG-RANNode-ID							PRESENCE optional }|
	{ ID id-ManagementBasedMDTPLMNList			CRITICALITY ignore		TYPE MDTPLMNList									PRESENCE optional }|
	{ ID id-UEHistoryInformation				CRITICALITY ignore		TYPE UEHistoryInformation							PRESENCE optional }|
	{ ID id-UEHistoryInformationFromTheUE		CRITICALITY ignore		TYPE UEHistoryInformationFromTheUE				PRESENCE optional }|
	{ ID id-PSCellChangeHistory					CRITICALITY ignore		TYPE PSCellChangeHistory							PRESENCE optional }|
	{ ID id-IABNodeIndication					CRITICALITY reject		TYPE IABNodeIndication								PRESENCE optional }|
	{ ID id-NoPDUSessionIndication				CRITICALITY ignore		TYPE NoPDUSessionIndication						PRESENCE optional }|
	{ ID id-CHOinformation-AddReq				CRITICALITY reject		TYPE CHOinformation-AddReq						PRESENCE optional }|
	{ ID id-SCGActivationRequest				CRITICALITY ignore		TYPE SCGActivationRequest							PRESENCE optional }|
	{ ID id-CPAInformationRequest				CRITICALITY reject		TYPE CPAInformationRequest						PRESENCE optional }|
	{ ID id-S-NG-RANnodeUE-Slice-MBR				CRITICALITY reject		TYPE UESliceMaximumBitRateList					PRESENCE optional }|
	{ ID id-F1-terminatingIAB-donorIndicator		CRITICALITY reject		TYPE F1-terminatingIAB-donorIndicator			PRESENCE optional },
	...
}

PDUSessionToBeAddedAddReq ::= SEQUENCE (SIZE(1..maxnoofPDUSessions)) OF PDUSessionToBeAddedAddReq-Item

PDUSessionToBeAddedAddReq-Item ::= SEQUENCE {
	pduSessionId			PDUSession-ID,
	s-NSSAI					S-NSSAI,
	sN-PDUSessionAMBR		PDUSessionAggregateMaximumBitRate			OPTIONAL,
	sn-terminated			PDUSessionResourceSetupInfo-SNterminated	OPTIONAL,
	mn-terminated			PDUSessionResourceSetupInfo-MNterminated	OPTIONAL,
-- NOTE: If neither the PDU Session Resource Setup Info - SN terminated IE
-- nor the PDU Session Resource Setup Info - MN terminated IE is present,
-- abnormal conditions as specified in clause 8.3.1.4 apply.
	iE-Extension			ProtocolExtensionContainer { {PDUSessionToBeAddedAddReq-Item-ExtIEs} }	OPTIONAL,
	...
}

PDUSessionToBeAddedAddReq-Item-ExtIEs XNAP-PROTOCOL-EXTENSION ::= {
	...
}

RequestedFastMCGRecoveryViaSRB3 ::= ENUMERATED {true, ...}

-- **************************************************************
--
-- S-NODE ADDITION REQUEST ACKNOWLEDGE
--
-- **************************************************************

SNodeAdditionRequestAcknowledge ::= SEQUENCE {
	protocolIEs			ProtocolIE-Container	{{ SNodeAdditionRequestAcknowledge-IEs}},
	...
}

SNodeAdditionRequestAcknowledge-IEs XNAP-PROTOCOL-IES ::= {
	{ ID id-M-NG-RANnodeUEXnAPID				CRITICALITY reject		TYPE NG-RANnodeUEXnAPID							PRESENCE mandatory}|
	{ ID id-S-NG-RANnodeUEXnAPID				CRITICALITY reject		TYPE NG-RANnodeUEXnAPID							PRESENCE mandatory}|
	{ ID id-PDUSessionAdmittedAddedAddReqAck	CRITICALITY ignore		TYPE PDUSessionAdmittedAddedAddReqAck		PRESENCE mandatory}|
	{ ID id-PDUSessionNotAdmittedAddReqAck		CRITICALITY ignore		TYPE PDUSessionNotAdmittedAddReqAck		PRESENCE optional }|
	{ ID id-SN-to-MN-Container					CRITICALITY reject		TYPE OCTET STRING								PRESENCE mandatory}|
	{ ID id-admittedSplitSRB					CRITICALITY reject		TYPE SplitSRBsTypes								PRESENCE optional }|
	{ ID id-RRCConfigIndication					CRITICALITY reject		TYPE RRCConfigIndication						PRESENCE optional }|
	{ ID id-CriticalityDiagnostics				CRITICALITY ignore		TYPE CriticalityDiagnostics					PRESENCE optional }|
	{ ID id-LocationInformationSN				CRITICALITY ignore		TYPE Target-CGI									PRESENCE optional }|
	{ ID id-MR-DC-ResourceCoordinationInfo		CRITICALITY ignore		TYPE MR-DC-ResourceCoordinationInfo		PRESENCE optional }|
	{ ID id-AvailableFastMCGRecoveryViaSRB3		CRITICALITY ignore		TYPE AvailableFastMCGRecoveryViaSRB3		PRESENCE optional }|
	{ ID id-DirectForwardingPathAvailability	CRITICALITY ignore		TYPE DirectForwardingPathAvailability		PRESENCE optional }|
	{ ID id-SCGActivationStatus					CRITICALITY ignore		TYPE SCGActivationStatus						PRESENCE optional	}|
	{ ID id-CPAInformationAck					CRITICALITY ignore		TYPE CPAInformationAck							PRESENCE optional },
	...
}

PDUSessionAdmittedAddedAddReqAck ::= SEQUENCE (SIZE(1..maxnoofPDUSessions)) OF PDUSessionAdmittedAddedAddReqAck-Item

PDUSessionAdmittedAddedAddReqAck-Item ::= SEQUENCE {
	pduSessionId							PDUSession-ID,
	sn-terminated			PDUSessionResourceSetupResponseInfo-SNterminated	OPTIONAL,
	mn-terminated			PDUSessionResourceSetupResponseInfo-MNterminated	OPTIONAL,
-- NOTE: If neither the PDU Session Resource Setup Response Info - SN terminated IE
-- nor the PDU Session Resource Setup Response Info - MN terminated IE is present,
-- abnormal conditions as specified in clause 8.3.1.4 apply.
	iE-Extension			ProtocolExtensionContainer { {PDUSessionAdmittedAddedAddReqAck-Item-ExtIEs} }	OPTIONAL,
	...
}

PDUSessionAdmittedAddedAddReqAck-Item-ExtIEs XNAP-PROTOCOL-EXTENSION ::= {
	...
}

PDUSessionNotAdmittedAddReqAck ::= SEQUENCE {
	pduSessionResourcesNotAdmitted-SNterminated		PDUSessionResourcesNotAdmitted-List OPTIONAL,
	pduSessionResourcesNotAdmitted-MNterminated		PDUSessionResourcesNotAdmitted-List OPTIONAL,
	iE-Extension			ProtocolExtensionContainer { {PDUSessionNotAdmittedAddReqAck-ExtIEs} }	OPTIONAL,
	...
}

PDUSessionNotAdmittedAddReqAck-ExtIEs XNAP-PROTOCOL-EXTENSION ::= {
	...
}

AvailableFastMCGRecoveryViaSRB3 ::= ENUMERATED {true, ...}

-- **************************************************************
--
-- S-NODE ADDITION REQUEST REJECT
--
-- **************************************************************

SNodeAdditionRequestReject ::= SEQUENCE {
	protocolIEs			ProtocolIE-Container	{{ SNodeAdditionRequestReject-IEs}},
	...
}

SNodeAdditionRequestReject-IEs XNAP-PROTOCOL-IES ::= {
	{ ID id-M-NG-RANnodeUEXnAPID					CRITICALITY reject		TYPE NG-RANnodeUEXnAPID							PRESENCE mandatory}|
	{ ID id-S-NG-RANnodeUEXnAPID					CRITICALITY reject		TYPE NG-RANnodeUEXnAPID							PRESENCE mandatory}|
	{ ID id-Cause									CRITICALITY ignore		TYPE Cause											PRESENCE mandatory}|
	{ ID id-CriticalityDiagnostics					CRITICALITY ignore		TYPE CriticalityDiagnostics						PRESENCE optional },
	...
}

-- **************************************************************
--
-- S-NODE RECONFIGURATION COMPLETE
--
-- **************************************************************

SNodeReconfigurationComplete ::= SEQUENCE {
	protocolIEs			ProtocolIE-Container	{{ SNodeReconfigurationComplete-IEs}},
	...
}

SNodeReconfigurationComplete-IEs XNAP-PROTOCOL-IES ::= {
	{ ID id-M-NG-RANnodeUEXnAPID					CRITICALITY reject		TYPE NG-RANnodeUEXnAPID							PRESENCE mandatory}|
	{ ID id-S-NG-RANnodeUEXnAPID					CRITICALITY reject		TYPE NG-RANnodeUEXnAPID							PRESENCE mandatory}|
	{ ID id-ResponseInfo-ReconfCompl				CRITICALITY ignore		TYPE ResponseInfo-ReconfCompl					PRESENCE mandatory},
	...
}

ResponseInfo-ReconfCompl ::= SEQUENCE {
	responseType-ReconfComplete		ResponseType-ReconfComplete,
	iE-Extensions						ProtocolExtensionContainer { {ResponseInfo-ReconfCompl-ExtIEs} } OPTIONAL,
	...
}

ResponseInfo-ReconfCompl-ExtIEs XNAP-PROTOCOL-EXTENSION ::= {
	...
}

ResponseType-ReconfComplete ::= CHOICE {
	configuration-successfully-applied			Configuration-successfully-applied,
	configuration-rejected-by-M-NG-RANNode		Configuration-rejected-by-M-NG-RANNode,
	choice-extension					ProtocolIE-Single-Container { {ResponseType-ReconfComplete-ExtIEs} }
}

ResponseType-ReconfComplete-ExtIEs XNAP-PROTOCOL-IES ::= {
	...
}

Configuration-successfully-applied ::= SEQUENCE {
	m-NG-RANNode-to-S-NG-RANNode-Container		OCTET STRING		OPTIONAL,
	iE-Extensions						ProtocolExtensionContainer { {Configuration-successfully-applied-ExtIEs} } OPTIONAL,
	...
}

Configuration-successfully-applied-ExtIEs XNAP-PROTOCOL-EXTENSION ::= {
	...
}

Configuration-rejected-by-M-NG-RANNode ::= SEQUENCE {
	cause											Cause,
	m-NG-RANNode-to-S-NG-RANNode-Container		OCTET STRING		OPTIONAL,
	iE-Extensions						ProtocolExtensionContainer { {Configuration-rejected-by-M-NG-RANNode-ExtIEs} } OPTIONAL,
	...
}

Configuration-rejected-by-M-NG-RANNode-ExtIEs XNAP-PROTOCOL-EXTENSION ::= {
	...
}


-- **************************************************************
--
-- S-NODE MODIFICATION REQUEST
--
-- **************************************************************

SNodeModificationRequest ::= SEQUENCE {
	protocolIEs			ProtocolIE-Container	{{ SNodeModificationRequest-IEs}},
	...
}

SNodeModificationRequest-IEs XNAP-PROTOCOL-IES ::= {
	{ ID id-M-NG-RANnodeUEXnAPID					CRITICALITY reject		TYPE NG-RANnodeUEXnAPID							PRESENCE mandatory}|
	{ ID id-S-NG-RANnodeUEXnAPID					CRITICALITY reject		TYPE NG-RANnodeUEXnAPID							PRESENCE mandatory}|
	{ ID id-Cause									CRITICALITY ignore		TYPE Cause											PRESENCE mandatory}|
	{ ID id-PDCPChangeIndication					CRITICALITY ignore		TYPE PDCPChangeIndication						PRESENCE optional }|
	{ ID id-selectedPLMN							CRITICALITY ignore		TYPE PLMN-Identity									PRESENCE optional }|
	{ ID id-MobilityRestrictionList					CRITICALITY ignore		TYPE MobilityRestrictionList					PRESENCE optional }|
	{ ID id-SCGConfigurationQuery					CRITICALITY ignore		TYPE SCGConfigurationQuery						PRESENCE optional }|
	{ ID id-UEContextInfo-SNModRequest				CRITICALITY reject		TYPE UEContextInfo-SNModRequest				PRESENCE optional }|
	{ ID id-MN-to-SN-Container						CRITICALITY ignore		TYPE OCTET STRING									PRESENCE optional }|
	{ ID id-requestedSplitSRB						CRITICALITY ignore		TYPE SplitSRBsTypes									PRESENCE optional }|
	{ ID id-requestedSplitSRBrelease				CRITICALITY ignore		TYPE SplitSRBsTypes									PRESENCE optional }|
	{ ID id-DesiredActNotificationLevel				CRITICALITY ignore		TYPE DesiredActNotificationLevel				PRESENCE optional }|
	{ ID id-AdditionalDRBIDs						CRITICALITY reject		TYPE DRB-List										PRESENCE optional }|
	{ ID id-S-NG-RANnodeMaxIPDataRate-UL			CRITICALITY reject		TYPE BitRate										PRESENCE optional }|
	{ ID id-S-NG-RANnodeMaxIPDataRate-DL			CRITICALITY reject		TYPE BitRate										PRESENCE optional }|
	{ ID id-LocationInformationSNReporting			CRITICALITY ignore		TYPE LocationInformationSNReporting			PRESENCE optional }|
	{ ID id-MR-DC-ResourceCoordinationInfo			CRITICALITY ignore		TYPE MR-DC-ResourceCoordinationInfo			PRESENCE optional }|
	{ ID id-PCellID									CRITICALITY reject		TYPE GlobalNG-RANCell-ID							PRESENCE optional }|
	{ ID id-NE-DC-TDM-Pattern						CRITICALITY ignore		TYPE NE-DC-TDM-Pattern							PRESENCE optional}|
	{ ID id-RequestedFastMCGRecoveryViaSRB3			CRITICALITY ignore		TYPE RequestedFastMCGRecoveryViaSRB3			PRESENCE optional }|
	{ ID id-RequestedFastMCGRecoveryViaSRB3Release	CRITICALITY ignore		TYPE RequestedFastMCGRecoveryViaSRB3Release	PRESENCE optional }|
	{ ID id-SNTriggered								CRITICALITY ignore		TYPE SNTriggered									PRESENCE optional }|
	{ ID id-TargetNodeID							CRITICALITY ignore		TYPE GlobalNG-RANNode-ID							PRESENCE optional }|
	{ ID id-PSCellHistoryInformationRetrieve		CRITICALITY ignore		TYPE PSCellHistoryInformationRetrieve		PRESENCE optional }|
	{ ID id-UEHistoryInformationFromTheUE			CRITICALITY ignore		TYPE UEHistoryInformationFromTheUE			PRESENCE optional }|
	{ ID id-CHOinformation-ModReq					CRITICALITY ignore		TYPE CHOinformation-ModReq						PRESENCE optional }|
	{ ID id-SCGActivationRequest					CRITICALITY ignore		TYPE SCGActivationRequest						PRESENCE optional }|
	{ ID id-CPAInformationModReq					CRITICALITY ignore		TYPE CPAInformationModReq						PRESENCE optional }|
	{ ID id-CPCInformationUpdate					CRITICALITY ignore		TYPE CPCInformationUpdate						PRESENCE optional }|
	{ ID id-S-NG-RANnodeUE-Slice-MBR					CRITICALITY ignore		TYPE UESliceMaximumBitRateList					PRESENCE optional }|
	{ ID id-ManagementBasedMDTPLMNModificationList	CRITICALITY	ignore		TYPE MDTPLMNModificationList					PRESENCE optional },
	...
}

UEContextInfo-SNModRequest ::= SEQUENCE {
	ueSecurityCapabilities							UESecurityCapabilities								OPTIONAL,
	s-ng-RANnode-SecurityKey						S-NG-RANnode-SecurityKey							OPTIONAL,
	s-ng-RANnodeUE-AMBR								UEAggregateMaximumBitRate							OPTIONAL,
	indexToRatFrequencySelectionPriority			RFSP-Index											OPTIONAL,
	lowerLayerPresenceStatusChange					LowerLayerPresenceStatusChange						OPTIONAL,
	pduSessionResourceToBeAdded						PDUSessionsToBeAdded-SNModRequest-List				OPTIONAL,
	pduSessionResourceToBeModified					PDUSessionsToBeModified-SNModRequest-List			OPTIONAL,
	pduSessionResourceToBeReleased					PDUSessionsToBeReleased-SNModRequest-List			OPTIONAL,
	iE-Extension			ProtocolExtensionContainer { {UEContextInfo-SNModRequest-ExtIEs} }			OPTIONAL,
	...
}

UEContextInfo-SNModRequest-ExtIEs XNAP-PROTOCOL-EXTENSION ::= {
	...
}

PDUSessionsToBeAdded-SNModRequest-List ::= SEQUENCE (SIZE(1..maxnoofPDUSessions)) OF PDUSessionsToBeAdded-SNModRequest-Item

PDUSessionsToBeAdded-SNModRequest-Item ::= SEQUENCE {
	pduSessionId			PDUSession-ID,
	s-NSSAI					S-NSSAI,
	sN-PDUSessionAMBR		PDUSessionAggregateMaximumBitRate			OPTIONAL,
	sn-terminated			PDUSessionResourceSetupInfo-SNterminated	OPTIONAL,
	mn-terminated			PDUSessionResourceSetupInfo-MNterminated	OPTIONAL,
-- NOTE: If neither the PDU Session Resource Setup Info - SN terminated IE
-- nor the PDU Session Resource Setup Info - MN terminated IE is present,
-- abnormal conditions as specified in clause 8.3.3.4 apply.
	iE-Extension			ProtocolExtensionContainer { {PDUSessionsToBeAdded-SNModRequest-Item-ExtIEs} }	OPTIONAL,
	...
}

PDUSessionsToBeAdded-SNModRequest-Item-ExtIEs XNAP-PROTOCOL-EXTENSION ::= {
	{ID id-PDUSessionExpectedUEActivityBehaviour		CRITICALITY ignore	EXTENSION ExpectedUEActivityBehaviour		PRESENCE optional},
	...
}

PDUSessionsToBeModified-SNModRequest-List ::= SEQUENCE (SIZE(1..maxnoofPDUSessions)) OF PDUSessionsToBeModified-SNModRequest-Item

PDUSessionsToBeModified-SNModRequest-Item ::= SEQUENCE {
	pduSessionId			PDUSession-ID,
	sN-PDUSessionAMBR		PDUSessionAggregateMaximumBitRate				OPTIONAL,
	sn-terminated			PDUSessionResourceModificationInfo-SNterminated	OPTIONAL,
	mn-terminated			PDUSessionResourceModificationInfo-MNterminated	OPTIONAL,
-- NOTE: If neither the PDU Session Resource Modification Info - SN terminated IE
-- nor the PDU Session Resource Modification Info - MN terminated IE is present,
-- abnormal conditions as specified in clause 8.3.3.4 apply.
	iE-Extension			ProtocolExtensionContainer { {PDUSessionsToBeModified-SNModRequest-Item-ExtIEs} }	OPTIONAL,
	...
}

PDUSessionsToBeModified-SNModRequest-Item-ExtIEs XNAP-PROTOCOL-EXTENSION ::= {
	{ID id-S-NSSAI		CRITICALITY reject	EXTENSION S-NSSAI		PRESENCE optional}|
	{ID id-PDUSessionExpectedUEActivityBehaviour		CRITICALITY ignore	EXTENSION ExpectedUEActivityBehaviour		PRESENCE optional},
	...
}

PDUSessionsToBeReleased-SNModRequest-List ::= SEQUENCE {
	pdu-session-list		PDUSession-List-withCause				OPTIONAL,
	iE-Extension			ProtocolExtensionContainer { {PDUSessionsToBeReleased-SNModRequest-List-ExtIEs} }	OPTIONAL,
	...
}

PDUSessionsToBeReleased-SNModRequest-List-ExtIEs XNAP-PROTOCOL-EXTENSION ::= {
	...
}

RequestedFastMCGRecoveryViaSRB3Release ::= ENUMERATED {true, ...}

-- **************************************************************
--
-- S-NODE MODIFICATION REQUEST ACKNOWLEDGE
--
-- **************************************************************

SNodeModificationRequestAcknowledge ::= SEQUENCE {
	protocolIEs			ProtocolIE-Container	{{ SNodeModificationRequestAcknowledge-IEs}},
	...
}

SNodeModificationRequestAcknowledge-IEs XNAP-PROTOCOL-IES ::= {
	{ ID id-M-NG-RANnodeUEXnAPID					CRITICALITY ignore		TYPE NG-RANnodeUEXnAPID								PRESENCE mandatory}|
	{ ID id-S-NG-RANnodeUEXnAPID					CRITICALITY ignore		TYPE NG-RANnodeUEXnAPID								PRESENCE mandatory}|
	{ ID id-PDUSessionAdmitted-SNModResponse		CRITICALITY ignore		TYPE PDUSessionAdmitted-SNModResponse			PRESENCE optional }|
	{ ID id-PDUSessionNotAdmitted-SNModResponse		CRITICALITY ignore		TYPE PDUSessionNotAdmitted-SNModResponse		PRESENCE optional }|
	{ ID id-SN-to-MN-Container						CRITICALITY ignore		TYPE OCTET STRING										PRESENCE optional }|
	{ ID id-admittedSplitSRB						CRITICALITY ignore		TYPE SplitSRBsTypes										PRESENCE optional }|
	{ ID id-admittedSplitSRBrelease					CRITICALITY ignore		TYPE SplitSRBsTypes										PRESENCE optional }|
	{ ID id-CriticalityDiagnostics					CRITICALITY ignore		TYPE CriticalityDiagnostics							PRESENCE optional }|
	{ ID id-LocationInformationSN					CRITICALITY ignore		TYPE Target-CGI											PRESENCE optional }|
	{ ID id-MR-DC-ResourceCoordinationInfo			CRITICALITY ignore		TYPE MR-DC-ResourceCoordinationInfo				PRESENCE optional }|
	{ ID id-PDUSessionDataForwarding-SNModResponse	CRITICALITY ignore		TYPE PDUSessionDataForwarding-SNModResponse	PRESENCE optional }|
	{ ID id-RRCConfigIndication						CRITICALITY reject		TYPE RRCConfigIndication								PRESENCE optional }|
	{ ID id-AvailableFastMCGRecoveryViaSRB3			CRITICALITY ignore		TYPE AvailableFastMCGRecoveryViaSRB3				PRESENCE optional }|
	{ ID id-ReleaseFastMCGRecoveryViaSRB3			CRITICALITY ignore		TYPE ReleaseFastMCGRecoveryViaSRB3				PRESENCE optional }|
	{ ID id-DirectForwardingPathAvailability		CRITICALITY ignore		TYPE DirectForwardingPathAvailability			PRESENCE optional }|
	{ ID id-SCGUEHistoryInformation					CRITICALITY ignore		TYPE SCGUEHistoryInformation						PRESENCE optional }|
	{ ID id-SCGActivationStatus						CRITICALITY ignore		TYPE SCGActivationStatus								PRESENCE optional }|
	{ ID id-CPAInformationModReqAck					CRITICALITY ignore		TYPE CPAInformationModReqAck						PRESENCE optional },
	...
}
PDUSessionAdmitted-SNModResponse ::= SEQUENCE {
	pduSessionResourcesAdmittedToBeAdded			PDUSessionAdmittedToBeAddedSNModResponse 			OPTIONAL,
	pduSessionResourcesAdmittedToBeModified			PDUSessionAdmittedToBeModifiedSNModResponse 		OPTIONAL,
	pduSessionResourcesAdmittedToBeReleased			PDUSessionAdmittedToBeReleasedSNModResponse			OPTIONAL,
	iE-Extension			ProtocolExtensionContainer { {PDUSessionAdmitted-SNModResponse-ExtIEs} }	OPTIONAL,
	...
}

PDUSessionAdmitted-SNModResponse-ExtIEs XNAP-PROTOCOL-EXTENSION ::= {
	...
}

PDUSessionAdmittedToBeAddedSNModResponse ::= SEQUENCE (SIZE(1..maxnoofPDUSessions)) OF PDUSessionAdmittedToBeAddedSNModResponse-Item
PDUSessionAdmittedToBeAddedSNModResponse-Item ::= SEQUENCE {
	pduSessionId			PDUSession-ID,
	sn-terminated			PDUSessionResourceSetupResponseInfo-SNterminated	OPTIONAL,
	mn-terminated			PDUSessionResourceSetupResponseInfo-MNterminated	OPTIONAL,
-- NOTE: If neither the PDU Session Resource Setup Response Info - SN terminated IE
-- nor the PDU Session Resource Setup Response Info - MN terminated IE is present,
-- abnormal conditions as specified in clause 8.3.3.4 apply.
	iE-Extension			ProtocolExtensionContainer { {PDUSessionAdmittedToBeAddedSNModResponse-Item-ExtIEs} }	OPTIONAL,
	...
}

PDUSessionAdmittedToBeAddedSNModResponse-Item-ExtIEs XNAP-PROTOCOL-EXTENSION ::= {
	...
}

PDUSessionAdmittedToBeModifiedSNModResponse::= SEQUENCE (SIZE(1..maxnoofPDUSessions)) OF PDUSessionAdmittedToBeModifiedSNModResponse-Item
PDUSessionAdmittedToBeModifiedSNModResponse-Item ::= SEQUENCE {
	pduSessionId			PDUSession-ID,
	sn-terminated			PDUSessionResourceModificationResponseInfo-SNterminated	OPTIONAL,
	mn-terminated			PDUSessionResourceModificationResponseInfo-MNterminated	OPTIONAL,
-- NOTE: If neither the PDU Session Resource Modification Response Info - SN terminated IE
-- nor the PDU Session Resource Modification Response Info - MN terminated IE is present,
-- abnormal conditions as specified in clause 8.3.3.4 apply.
	iE-Extension			ProtocolExtensionContainer { {PDUSessionAdmittedToBeModifiedSNModResponse-Item-ExtIEs} }	OPTIONAL,
	...
}

PDUSessionAdmittedToBeModifiedSNModResponse-Item-ExtIEs XNAP-PROTOCOL-EXTENSION ::= {
	...
}

PDUSessionAdmittedToBeReleasedSNModResponse ::= SEQUENCE {
	sn-terminated			PDUSession-List-withDataForwardingRequest		OPTIONAL,
	mn-terminated			PDUSession-List-withCause						OPTIONAL,
	iE-Extension			ProtocolExtensionContainer { {PDUSessionAdmittedToBeReleasedSNModResponse-ExtIEs} }	OPTIONAL,
	...
}

PDUSessionAdmittedToBeReleasedSNModResponse-ExtIEs XNAP-PROTOCOL-EXTENSION ::= {
	...
}

PDUSessionNotAdmitted-SNModResponse ::= SEQUENCE {
	pdu-Session-List		PDUSession-List OPTIONAL,
	iE-Extension			ProtocolExtensionContainer { {PDUSessionNotAdmitted-SNModResponse-ExtIEs} }	OPTIONAL,
	...
}

PDUSessionNotAdmitted-SNModResponse-ExtIEs XNAP-PROTOCOL-EXTENSION ::= {
	...
}


PDUSessionDataForwarding-SNModResponse ::= SEQUENCE {
	sn-terminated		PDUSession-List-withDataForwardingRequest,
	iE-Extensions		ProtocolExtensionContainer { {PDUSessionDataForwarding-SNModResponse-ExtIEs} }	OPTIONAL,
	...
}

PDUSessionDataForwarding-SNModResponse-ExtIEs XNAP-PROTOCOL-EXTENSION ::= {
	...
}

ReleaseFastMCGRecoveryViaSRB3 ::= ENUMERATED {true, ...}



-- **************************************************************
--
-- S-NODE MODIFICATION REQUEST REJECT
--
-- **************************************************************

SNodeModificationRequestReject ::= SEQUENCE {
	protocolIEs			ProtocolIE-Container	{{ SNodeModificationRequestReject-IEs}},
	...
}

SNodeModificationRequestReject-IEs XNAP-PROTOCOL-IES ::= {
	{ ID id-M-NG-RANnodeUEXnAPID					CRITICALITY ignore		TYPE NG-RANnodeUEXnAPID							PRESENCE mandatory}|
	{ ID id-S-NG-RANnodeUEXnAPID					CRITICALITY ignore		TYPE NG-RANnodeUEXnAPID							PRESENCE mandatory}|
	{ ID id-Cause									CRITICALITY ignore		TYPE Cause											PRESENCE mandatory}|
	{ ID id-CriticalityDiagnostics					CRITICALITY ignore		TYPE CriticalityDiagnostics						PRESENCE optional },
	...
}

-- **************************************************************
--
-- S-NODE MODIFICATION REQUIRED
--
-- **************************************************************

SNodeModificationRequired ::= SEQUENCE {
	protocolIEs			ProtocolIE-Container	{{ SNodeModificationRequired-IEs}},
	...
}

SNodeModificationRequired-IEs XNAP-PROTOCOL-IES ::= {
	{ ID id-M-NG-RANnodeUEXnAPID					CRITICALITY reject		TYPE NG-RANnodeUEXnAPID							PRESENCE mandatory}|
	{ ID id-S-NG-RANnodeUEXnAPID					CRITICALITY reject		TYPE NG-RANnodeUEXnAPID							PRESENCE mandatory}|
	{ ID id-Cause									CRITICALITY ignore		TYPE Cause											PRESENCE mandatory}|
	{ ID id-PDCPChangeIndication					CRITICALITY ignore		TYPE PDCPChangeIndication						PRESENCE optional }|
	{ ID id-PDUSessionToBeModifiedSNModRequired		CRITICALITY ignore		TYPE PDUSessionToBeModifiedSNModRequired	PRESENCE optional }|
	{ ID id-PDUSessionToBeReleasedSNModRequired		CRITICALITY ignore		TYPE PDUSessionToBeReleasedSNModRequired	PRESENCE optional }|
	{ ID id-SN-to-MN-Container						CRITICALITY ignore		TYPE OCTET STRING									PRESENCE optional }|
	{ ID id-SpareDRBIDs								CRITICALITY ignore		TYPE DRB-List										PRESENCE optional }|
	{ ID id-RequiredNumberOfDRBIDs					CRITICALITY ignore		TYPE DRB-Number										PRESENCE optional }|
	{ ID id-LocationInformationSN					CRITICALITY ignore		TYPE Target-CGI										PRESENCE optional }|
	{ ID id-MR-DC-ResourceCoordinationInfo			CRITICALITY ignore		TYPE MR-DC-ResourceCoordinationInfo			PRESENCE optional }|
	{ ID id-RRCConfigIndication						CRITICALITY reject		TYPE RRCConfigIndication							PRESENCE optional }|
	{ ID id-AvailableFastMCGRecoveryViaSRB3			CRITICALITY ignore		TYPE AvailableFastMCGRecoveryViaSRB3			PRESENCE optional }|
	{ ID id-ReleaseFastMCGRecoveryViaSRB3			CRITICALITY ignore		TYPE ReleaseFastMCGRecoveryViaSRB3			PRESENCE optional }|
	{ ID id-SCGIndicator							CRITICALITY ignore		TYPE SCGIndicator									PRESENCE optional }|
	{ ID id-SCGUEHistoryInformation					CRITICALITY ignore		TYPE SCGUEHistoryInformation					PRESENCE optional }|
	{ ID id-SCGActivationRequest					CRITICALITY ignore		TYPE SCGActivationRequest						PRESENCE optional }|
	{ ID id-CPACInformationModRequired				CRITICALITY ignore		TYPE CPACInformationModRequired				PRESENCE optional }|
	{ ID id-SCGreconfigNotification					CRITICALITY ignore		TYPE SCGreconfigNotification					PRESENCE optional },
	...
}
PDUSessionToBeModifiedSNModRequired::= SEQUENCE (SIZE (1.. maxnoofPDUSessions)) OF 	PDUSessionToBeModifiedSNModRequired-Item

PDUSessionToBeModifiedSNModRequired-Item ::= SEQUENCE {
	pduSessionId						PDUSession-ID,
	sn-terminated			PDUSessionResourceModRqdInfo-SNterminated	OPTIONAL,
	mn-terminated			PDUSessionResourceModRqdInfo-MNterminated	OPTIONAL,
-- NOTE: If neither the PDU Session Resource Modification Required Info - SN terminated IE
-- nor the PDU Session Resource Modification Required Info - MN terminated IE is present,
-- abnormal conditions as specified in clause 8.3.4.4 apply.
	iE-Extension		ProtocolExtensionContainer { {PDUSessionToBeModifiedSNModRequired-Item-ExtIEs} }	OPTIONAL,
	...
}

PDUSessionToBeModifiedSNModRequired-Item-ExtIEs XNAP-PROTOCOL-EXTENSION ::= {
	...
}

PDUSessionToBeReleasedSNModRequired ::= SEQUENCE {
	sn-terminated			PDUSession-List-withDataForwardingRequest		OPTIONAL,
	mn-terminated			PDUSession-List-withCause						OPTIONAL,
	iE-Extension			ProtocolExtensionContainer { {PDUSessionToBeReleasedSNModRequired-ExtIEs} } OPTIONAL,
	...
}

PDUSessionToBeReleasedSNModRequired-ExtIEs XNAP-PROTOCOL-EXTENSION ::= {
	...
}

-- **************************************************************
--
-- S-NODE MODIFICATION CONFIRM
--
-- **************************************************************

SNodeModificationConfirm ::= SEQUENCE {
	protocolIEs			ProtocolIE-Container	{{ SNodeModificationConfirm-IEs}},
	...
}

SNodeModificationConfirm-IEs XNAP-PROTOCOL-IES ::= {
	{ ID id-M-NG-RANnodeUEXnAPID					CRITICALITY ignore		TYPE NG-RANnodeUEXnAPID							PRESENCE mandatory}|
	{ ID id-S-NG-RANnodeUEXnAPID					CRITICALITY ignore		TYPE NG-RANnodeUEXnAPID							PRESENCE mandatory}|
	{ ID id-PDUSessionAdmittedModSNModConfirm		CRITICALITY ignore		TYPE PDUSessionAdmittedModSNModConfirm		PRESENCE optional }|
	{ ID id-PDUSessionReleasedSNModConfirm			CRITICALITY ignore		TYPE PDUSessionReleasedSNModConfirm			PRESENCE optional }|
	{ ID id-MN-to-SN-Container						CRITICALITY ignore		TYPE OCTET STRING									PRESENCE optional }|
	{ ID id-AdditionalDRBIDs						CRITICALITY reject		TYPE DRB-List										PRESENCE optional }|
	{ ID id-CriticalityDiagnostics					CRITICALITY ignore		TYPE CriticalityDiagnostics						PRESENCE optional }|
	{ ID id-MR-DC-ResourceCoordinationInfo			CRITICALITY ignore		TYPE MR-DC-ResourceCoordinationInfo			PRESENCE optional },
	...
}

PDUSessionAdmittedModSNModConfirm ::= SEQUENCE (SIZE(1..maxnoofPDUSessions)) OF PDUSessionAdmittedModSNModConfirm-Item

PDUSessionAdmittedModSNModConfirm-Item ::= SEQUENCE {
	pduSessionId				PDUSession-ID,
	sn-terminated			PDUSessionResourceModConfirmInfo-SNterminated	OPTIONAL,
	mn-terminated			PDUSessionResourceModConfirmInfo-MNterminated	OPTIONAL,
-- NOTE: If neither the PDU Session Resource Modification Confirm Info - SN terminated IE
-- nor the PDU Session Resource Modification Confirm Info - MN terminated IE is present,
-- abnormal conditions as specified in clause 8.3.4.4 apply.
	iE-Extension			ProtocolExtensionContainer { {PDUSessionAdmittedModSNModConfirm-Item-ExtIEs} }	OPTIONAL,
	...
}

PDUSessionAdmittedModSNModConfirm-Item-ExtIEs XNAP-PROTOCOL-EXTENSION ::= {
	...
}


PDUSessionReleasedSNModConfirm ::= SEQUENCE {
	sn-terminated			PDUSession-List-withDataForwardingFromTarget						OPTIONAL,
	mn-terminated			PDUSession-List														OPTIONAL,
	iE-Extension			ProtocolExtensionContainer { {PDUSessionAdmittedToBeReleasedSNModConfirm-ExtIEs} }	OPTIONAL,
	...
}

PDUSessionAdmittedToBeReleasedSNModConfirm-ExtIEs XNAP-PROTOCOL-EXTENSION ::= {
	...
}


-- **************************************************************
--
-- S-NODE MODIFICATION REFUSE
--
-- **************************************************************

SNodeModificationRefuse ::= SEQUENCE {
	protocolIEs			ProtocolIE-Container	{{ SNodeModificationRefuse-IEs}},
	...
}

SNodeModificationRefuse-IEs XNAP-PROTOCOL-IES ::= {
	{ ID id-M-NG-RANnodeUEXnAPID					CRITICALITY ignore		TYPE NG-RANnodeUEXnAPID							PRESENCE mandatory}|
	{ ID id-S-NG-RANnodeUEXnAPID					CRITICALITY ignore		TYPE NG-RANnodeUEXnAPID							PRESENCE mandatory}|
	{ ID id-Cause									CRITICALITY ignore		TYPE Cause											PRESENCE mandatory}|
	{ ID id-MN-to-SN-Container						CRITICALITY ignore		TYPE OCTET STRING									PRESENCE optional }|
	{ ID id-CriticalityDiagnostics					CRITICALITY ignore		TYPE CriticalityDiagnostics						PRESENCE optional },
	...
}

-- **************************************************************
--
-- S-NODE RELEASE REQUEST
--
-- **************************************************************

SNodeReleaseRequest ::= SEQUENCE {
	protocolIEs			ProtocolIE-Container	{{ SNodeReleaseRequest-IEs}},
	...
}

SNodeReleaseRequest-IEs XNAP-PROTOCOL-IES ::= {
	{ ID id-M-NG-RANnodeUEXnAPID					CRITICALITY reject		TYPE NG-RANnodeUEXnAPID							PRESENCE mandatory}|
	{ ID id-S-NG-RANnodeUEXnAPID					CRITICALITY reject		TYPE NG-RANnodeUEXnAPID							PRESENCE optional }|
	{ ID id-Cause									CRITICALITY ignore		TYPE Cause											PRESENCE mandatory}|
	{ ID id-PDUSessionToBeReleased-RelReq			CRITICALITY ignore		TYPE PDUSession-List-withCause					PRESENCE optional}|
	{ ID id-UEContextKeptIndicator					CRITICALITY ignore		TYPE UEContextKeptIndicator						PRESENCE optional }|
	{ ID id-MN-to-SN-Container						CRITICALITY ignore		TYPE OCTET STRING									PRESENCE optional }|
	{ ID id-DRBs-transferred-to-MN					CRITICALITY ignore		TYPE DRB-List										PRESENCE optional },
	...
}

-- **************************************************************
--
-- S-NODE RELEASE REQUEST ACKNOWLEDGE
--
-- **************************************************************

SNodeReleaseRequestAcknowledge ::= SEQUENCE {
	protocolIEs			ProtocolIE-Container	{{ SNodeReleaseRequestAcknowledge-IEs}},
	...
}

SNodeReleaseRequestAcknowledge-IEs XNAP-PROTOCOL-IES ::= {
	{ ID id-M-NG-RANnodeUEXnAPID						CRITICALITY reject		TYPE NG-RANnodeUEXnAPID									PRESENCE mandatory}|
	{ ID id-S-NG-RANnodeUEXnAPID						CRITICALITY reject		TYPE NG-RANnodeUEXnAPID									PRESENCE optional }|
	{ ID id-PDUSessionToBeReleased-RelReqAck			CRITICALITY ignore		TYPE PDUSessionToBeReleasedList-RelReqAck			PRESENCE optional	}|
	{ ID id-CriticalityDiagnostics						CRITICALITY ignore		TYPE CriticalityDiagnostics							PRESENCE optional }|
	{ ID id-SCGUEHistoryInformation						CRITICALITY ignore		TYPE SCGUEHistoryInformation							PRESENCE optional },
	...
}

PDUSessionToBeReleasedList-RelReqAck ::= SEQUENCE {
	pduSessionsToBeReleasedList-SNterminated		PDUSession-List-withDataForwardingRequest												OPTIONAL,
	iE-Extensions									ProtocolExtensionContainer { {PDUSessionToBeReleasedList-RelReqAck-ExtIEs} }	OPTIONAL,
	...
}

PDUSessionToBeReleasedList-RelReqAck-ExtIEs XNAP-PROTOCOL-EXTENSION ::= {
	...
}

-- **************************************************************
--
-- S-NODE RELEASE REJECT
--
-- **************************************************************

SNodeReleaseReject ::= SEQUENCE {
	protocolIEs			ProtocolIE-Container	{{ SNodeReleaseReject-IEs}},
	...
}

SNodeReleaseReject-IEs XNAP-PROTOCOL-IES ::= {
	{ ID id-M-NG-RANnodeUEXnAPID					CRITICALITY reject		TYPE NG-RANnodeUEXnAPID							PRESENCE mandatory}|
	{ ID id-S-NG-RANnodeUEXnAPID					CRITICALITY reject		TYPE NG-RANnodeUEXnAPID							PRESENCE optional }|
	{ ID id-Cause									CRITICALITY ignore		TYPE Cause											PRESENCE mandatory}|
	{ ID id-CriticalityDiagnostics					CRITICALITY ignore		TYPE CriticalityDiagnostics						PRESENCE optional },
	...
}

-- **************************************************************
--
-- S-NODE RELEASE REQUIRED
--
-- **************************************************************

SNodeReleaseRequired ::= SEQUENCE {
	protocolIEs			ProtocolIE-Container	{{ SNodeReleaseRequired-IEs}},
	...
}

SNodeReleaseRequired-IEs XNAP-PROTOCOL-IES ::= {
	{ ID id-M-NG-RANnodeUEXnAPID					CRITICALITY reject		TYPE NG-RANnodeUEXnAPID							PRESENCE mandatory}|
	{ ID id-S-NG-RANnodeUEXnAPID					CRITICALITY reject		TYPE NG-RANnodeUEXnAPID							PRESENCE mandatory}|
	{ ID id-PDUSessionToBeReleasedList-RelRqd		CRITICALITY ignore		TYPE PDUSessionToBeReleasedList-RelRqd		PRESENCE optional }|
	{ ID id-Cause									CRITICALITY ignore		TYPE Cause											PRESENCE mandatory}|
	{ ID id-SN-to-MN-Container						CRITICALITY ignore		TYPE OCTET STRING									PRESENCE optional }|
	{ ID id-SCGUEHistoryInformation					CRITICALITY ignore		TYPE SCGUEHistoryInformation					PRESENCE optional },
	...
}

PDUSessionToBeReleasedList-RelRqd ::= SEQUENCE {
	pduSessionsToBeReleasedList-SNterminated		PDUSession-List-withDataForwardingRequest						OPTIONAL,
	iE-Extensions					ProtocolExtensionContainer { {PDUSessionToBeReleasedList-RelRqd-ExtIEs} }	OPTIONAL,
	...
}

PDUSessionToBeReleasedList-RelRqd-ExtIEs XNAP-PROTOCOL-EXTENSION ::= {
	...
}


-- **************************************************************
--
-- S-NODE RELEASE CONFIRM
--
-- **************************************************************

SNodeReleaseConfirm ::= SEQUENCE {
	protocolIEs			ProtocolIE-Container	{{ SNodeReleaseConfirm-IEs}},
	...
}

SNodeReleaseConfirm-IEs XNAP-PROTOCOL-IES ::= {
	{ ID id-M-NG-RANnodeUEXnAPID					CRITICALITY ignore		TYPE NG-RANnodeUEXnAPID							PRESENCE mandatory}|
	{ ID id-S-NG-RANnodeUEXnAPID					CRITICALITY ignore		TYPE NG-RANnodeUEXnAPID							PRESENCE mandatory}|
	{ ID id-PDUSessionReleasedList-RelConf			CRITICALITY ignore		TYPE PDUSessionReleasedList-RelConf			PRESENCE optional }|
	{ ID id-CriticalityDiagnostics					CRITICALITY ignore		TYPE CriticalityDiagnostics						PRESENCE optional },
	...
}

PDUSessionReleasedList-RelConf ::= SEQUENCE {
	pduSessionsReleasedList-SNterminated		PDUSession-List-withDataForwardingFromTarget					OPTIONAL,
	iE-Extensions					ProtocolExtensionContainer { {PDUSessionReleasedList-RelConf-ExtIEs} }	OPTIONAL,
	...
}

PDUSessionReleasedList-RelConf-ExtIEs XNAP-PROTOCOL-EXTENSION ::= {
	...
}


-- **************************************************************
--
-- S-NODE COUNTER CHECK REQUEST
--
-- **************************************************************

SNodeCounterCheckRequest ::= SEQUENCE {
	protocolIEs			ProtocolIE-Container	{{ SNodeCounterCheckRequest-IEs}},
	...
}

SNodeCounterCheckRequest-IEs XNAP-PROTOCOL-IES ::= {
	{ ID id-M-NG-RANnodeUEXnAPID					CRITICALITY ignore		TYPE NG-RANnodeUEXnAPID							PRESENCE mandatory}|
	{ ID id-S-NG-RANnodeUEXnAPID					CRITICALITY ignore		TYPE NG-RANnodeUEXnAPID							PRESENCE mandatory}|
	{ ID id-BearersSubjectToCounterCheck			CRITICALITY ignore		TYPE BearersSubjectToCounterCheck-List		PRESENCE mandatory},
	...
}

BearersSubjectToCounterCheck-List ::= SEQUENCE (SIZE(1..maxnoofDRBs)) OF BearersSubjectToCounterCheck-Item

BearersSubjectToCounterCheck-Item ::= SEQUENCE {
	drb-ID							DRB-ID,
	ul-count						INTEGER (0.. 4294967295),
	dl-count						INTEGER (0.. 4294967295),
	iE-Extensions					ProtocolExtensionContainer { {BearersSubjectToCounterCheck-Item-ExtIEs} }	OPTIONAL,
	...
}

BearersSubjectToCounterCheck-Item-ExtIEs XNAP-PROTOCOL-EXTENSION ::= {
	...
}


-- **************************************************************
--
-- S-NODE CHANGE REQUIRED
--
-- **************************************************************

SNodeChangeRequired ::= SEQUENCE {
	protocolIEs			ProtocolIE-Container	{{ SNodeChangeRequired-IEs}},
	...
}

SNodeChangeRequired-IEs XNAP-PROTOCOL-IES ::= {
	{ ID id-M-NG-RANnodeUEXnAPID					CRITICALITY reject		TYPE NG-RANnodeUEXnAPID							PRESENCE mandatory}|
	{ ID id-S-NG-RANnodeUEXnAPID					CRITICALITY reject		TYPE NG-RANnodeUEXnAPID							PRESENCE mandatory}|
	{ ID id-target-S-NG-RANnodeID					CRITICALITY reject		TYPE GlobalNG-RANNode-ID							PRESENCE mandatory}|
	{ ID id-Cause									CRITICALITY ignore		TYPE Cause											PRESENCE mandatory}|
	{ ID id-PDUSession-SNChangeRequired-List		CRITICALITY ignore		TYPE PDUSession-SNChangeRequired-List		PRESENCE optional }|
	{ ID id-SN-to-MN-Container						CRITICALITY reject		TYPE OCTET STRING									PRESENCE mandatory}|
	{ ID id-SCGUEHistoryInformation					CRITICALITY ignore		TYPE SCGUEHistoryInformation					PRESENCE optional }|
	{ ID id-SNMobilityInformation					CRITICALITY ignore		TYPE SNMobilityInformation						PRESENCE optional }|
	{ ID id-SourcePSCellID							CRITICALITY ignore		TYPE GlobalNG-RANCell-ID							PRESENCE optional }|
	{ ID id-CPCInformationRequired					CRITICALITY ignore		TYPE CPCInformationRequired						PRESENCE optional },
	...
}

PDUSession-SNChangeRequired-List ::= SEQUENCE (SIZE(1..maxnoofPDUSessions)) OF PDUSession-SNChangeRequired-Item

PDUSession-SNChangeRequired-Item ::= SEQUENCE {
	pduSessionId				PDUSession-ID,
	sn-terminated			PDUSessionResourceChangeRequiredInfo-SNterminated	OPTIONAL,
	mn-terminated			PDUSessionResourceChangeRequiredInfo-MNterminated	OPTIONAL,
-- NOTE: If the PDU Session Resource Change Required Info - SN terminated IE is not present,
-- abnormal conditions as specified in clause 8.3.5.4 apply.
	iE-Extension			ProtocolExtensionContainer { {PDUSession-SNChangeRequired-Item-ExtIEs} }	OPTIONAL,
	...
}

PDUSession-SNChangeRequired-Item-ExtIEs XNAP-PROTOCOL-EXTENSION ::= {
	...
}


-- **************************************************************
--
-- S-NODE CHANGE CONFIRM
--
-- **************************************************************

SNodeChangeConfirm ::= SEQUENCE {
	protocolIEs			ProtocolIE-Container	{{ SNodeChangeConfirm-IEs}},
	...
}

SNodeChangeConfirm-IEs XNAP-PROTOCOL-IES ::= {
	{ ID id-M-NG-RANnodeUEXnAPID					CRITICALITY ignore		TYPE NG-RANnodeUEXnAPID							PRESENCE mandatory}|
	{ ID id-S-NG-RANnodeUEXnAPID					CRITICALITY ignore		TYPE NG-RANnodeUEXnAPID							PRESENCE mandatory}|
	{ ID id-PDUSession-SNChangeConfirm-List			CRITICALITY ignore		TYPE PDUSession-SNChangeConfirm-List			PRESENCE optional }|
	{ ID id-CriticalityDiagnostics					CRITICALITY ignore		TYPE CriticalityDiagnostics						PRESENCE optional }|
	{ ID id-CPCInformationConfirm					CRITICALITY ignore		TYPE CPCInformationConfirm						PRESENCE optional }|
	{ ID id-MN-to-SN-Container						CRITICALITY ignore		TYPE OCTET STRING									PRESENCE optional },
	...
}
PDUSession-SNChangeConfirm-List ::= SEQUENCE (SIZE(1..maxnoofPDUSessions)) OF PDUSession-SNChangeConfirm-Item

PDUSession-SNChangeConfirm-Item ::= SEQUENCE {
	pduSessionId				PDUSession-ID,
	sn-terminated			PDUSessionResourceChangeConfirmInfo-SNterminated	OPTIONAL,
	mn-terminated			PDUSessionResourceChangeConfirmInfo-MNterminated	OPTIONAL,
-- NOTE: If the PDU Session Resource Change Confirm Info - SN terminated IE is not present,
-- abnormal conditions as specified in clause 8.3.5.4 apply.
	iE-Extension			ProtocolExtensionContainer { {PDUSession-SNChangeConfirm-Item-ExtIEs} }	OPTIONAL,
	...
}

PDUSession-SNChangeConfirm-Item-ExtIEs XNAP-PROTOCOL-EXTENSION ::= {
	{ ID id-AdditionalListofPDUSessionResourceChangeConfirmInfo-SNterminated		CRITICALITY ignore	EXTENSION			AdditionalListofPDUSessionResourceChangeConfirmInfo-SNterminated				PRESENCE optional},
	...
}


-- **************************************************************
--
-- S-NODE CHANGE REFUSE
--
-- **************************************************************

SNodeChangeRefuse ::= SEQUENCE {
	protocolIEs			ProtocolIE-Container	{{ SNodeChangeRefuse-IEs}},
	...
}

SNodeChangeRefuse-IEs XNAP-PROTOCOL-IES ::= {
	{ ID id-M-NG-RANnodeUEXnAPID					CRITICALITY ignore		TYPE NG-RANnodeUEXnAPID							PRESENCE mandatory}|
	{ ID id-S-NG-RANnodeUEXnAPID					CRITICALITY ignore		TYPE NG-RANnodeUEXnAPID							PRESENCE mandatory}|
	{ ID id-Cause									CRITICALITY ignore		TYPE Cause											PRESENCE mandatory}|
	{ ID id-CriticalityDiagnostics					CRITICALITY ignore		TYPE CriticalityDiagnostics						PRESENCE optional },
	...
}

-- **************************************************************
--
-- RRC TRANSFER
--
-- **************************************************************

RRCTransfer ::= SEQUENCE {
	protocolIEs			ProtocolIE-Container	{{ RRCTransfer-IEs}},
	...
}

RRCTransfer-IEs XNAP-PROTOCOL-IES ::= {
	{ ID id-M-NG-RANnodeUEXnAPID					CRITICALITY reject		TYPE NG-RANnodeUEXnAPID							PRESENCE mandatory}|
	{ ID id-S-NG-RANnodeUEXnAPID					CRITICALITY reject		TYPE NG-RANnodeUEXnAPID							PRESENCE mandatory}|
	{ ID id-SplitSRB-RRCTransfer					CRITICALITY reject		TYPE SplitSRB-RRCTransfer						PRESENCE optional }|
	{ ID id-UEReportRRCTransfer						CRITICALITY reject		TYPE UEReportRRCTransfer							PRESENCE optional }|
	{ ID id-FastMCGRecoveryRRCTransfer-SN-to-MN		CRITICALITY ignore		TYPE FastMCGRecoveryRRCTransfer				PRESENCE optional }|
	{ ID id-FastMCGRecoveryRRCTransfer-MN-to-SN		CRITICALITY ignore		TYPE FastMCGRecoveryRRCTransfer				PRESENCE optional }|
	{ ID id-SDT-SRB-between-NewNode-OldNode			CRITICALITY ignore		TYPE SDT-SRB-between-NewNode-OldNode			PRESENCE optional },
	...
}

SplitSRB-RRCTransfer ::= SEQUENCE {
	rrcContainer					OCTET STRING						OPTIONAL,
	srbType							ENUMERATED {srb1, srb2, ...},
	deliveryStatus					DeliveryStatus						OPTIONAL,
	iE-Extensions					ProtocolExtensionContainer { {SplitSRB-RRCTransfer-ExtIEs} } OPTIONAL,
	...
}

SplitSRB-RRCTransfer-ExtIEs XNAP-PROTOCOL-EXTENSION ::= {
	...
}

UEReportRRCTransfer::= SEQUENCE {
	rrcContainer					OCTET STRING,
	iE-Extensions					ProtocolExtensionContainer { {UEReportRRCTransfer-ExtIEs} } OPTIONAL,
	...
}

UEReportRRCTransfer-ExtIEs XNAP-PROTOCOL-EXTENSION ::= {
	...
}

FastMCGRecoveryRRCTransfer::= SEQUENCE {
	rrcContainer					OCTET STRING,
	iE-Extensions					ProtocolExtensionContainer { { FastMCGRecoveryRRCTransfer-ExtIEs} } OPTIONAL,
	...
}

FastMCGRecoveryRRCTransfer-ExtIEs XNAP-PROTOCOL-EXTENSION ::= {
	...
}

SDT-SRB-between-NewNode-OldNode::= SEQUENCE {
	rrcContainer					OCTET STRING,
	srb-ID							SRB-ID,
	iE-Extensions					ProtocolExtensionContainer { { SDT-SRB-between-NewNode-OldNode-ExtIEs} } OPTIONAL,
	...
}

SDT-SRB-between-NewNode-OldNode-ExtIEs XNAP-PROTOCOL-EXTENSION ::= {
	...
}

-- **************************************************************
--
-- NOTIFICATION CONTROL INDICATION
--
-- **************************************************************

NotificationControlIndication ::= SEQUENCE {
	protocolIEs			ProtocolIE-Container	{{NotificationControlIndication-IEs}},
	...
}

NotificationControlIndication-IEs XNAP-PROTOCOL-IES ::= {
	{ ID id-M-NG-RANnodeUEXnAPID				CRITICALITY reject		TYPE NG-RANnodeUEXnAPID							PRESENCE mandatory}|
	{ ID id-S-NG-RANnodeUEXnAPID				CRITICALITY reject		TYPE NG-RANnodeUEXnAPID							PRESENCE mandatory}|
	{ ID id-PDUSessionResourcesNotifyList		CRITICALITY reject		TYPE PDUSessionResourcesNotifyList			PRESENCE optional },
	...
}

PDUSessionResourcesNotifyList ::= SEQUENCE (SIZE(1..maxnoofPDUSessions)) OF PDUSessionResourcesNotify-Item

PDUSessionResourcesNotify-Item ::= SEQUENCE {
	pduSessionId						PDUSession-ID,
	qosFlowsNotificationContrIndInfo	QoSFlowNotificationControlIndicationInfo,
	iE-Extensions						ProtocolExtensionContainer { {PDUSessionResourcesNotify-Item-ExtIEs} } OPTIONAL,
	...
}

PDUSessionResourcesNotify-Item-ExtIEs XNAP-PROTOCOL-EXTENSION ::= {
	...
}

-- **************************************************************
--
-- ACTIVITY NOTIFICATION
--
-- **************************************************************

ActivityNotification ::= SEQUENCE {
	protocolIEs			ProtocolIE-Container	{{ActivityNotification-IEs}},
	...
}

ActivityNotification-IEs XNAP-PROTOCOL-IES ::= {
	{ ID id-M-NG-RANnodeUEXnAPID					CRITICALITY ignore		TYPE NG-RANnodeUEXnAPID							PRESENCE mandatory}|
	{ ID id-S-NG-RANnodeUEXnAPID					CRITICALITY ignore		TYPE NG-RANnodeUEXnAPID							PRESENCE mandatory}|
	{ ID id-UserPlaneTrafficActivityReport			CRITICALITY ignore		TYPE UserPlaneTrafficActivityReport			PRESENCE optional }|
	{ ID id-PDUSessionResourcesActivityNotifyList	CRITICALITY ignore		TYPE PDUSessionResourcesActivityNotifyList	PRESENCE optional }|
	{ ID id-RANPagingFailure						CRITICALITY ignore		TYPE RANPagingFailure								PRESENCE optional },
	...
}

PDUSessionResourcesActivityNotifyList ::= SEQUENCE (SIZE(1..maxnoofPDUSessions)) OF PDUSessionResourcesActivityNotify-Item

PDUSessionResourcesActivityNotify-Item ::= SEQUENCE {
	pduSessionId						PDUSession-ID,
	pduSessionLevelUPactivityreport		UserPlaneTrafficActivityReport											OPTIONAL,
	qosFlowsActivityNotifyList			QoSFlowsActivityNotifyList												OPTIONAL,
	iE-Extensions						ProtocolExtensionContainer { {PDUSessionResourcesActivityNotify-Item-ExtIEs} } OPTIONAL,
	...
}

PDUSessionResourcesActivityNotify-Item-ExtIEs XNAP-PROTOCOL-EXTENSION ::= {
	...
}

QoSFlowsActivityNotifyList ::= SEQUENCE (SIZE(1..maxnoofQoSFlows)) OF QoSFlowsActivityNotifyItem

QoSFlowsActivityNotifyItem ::= SEQUENCE {
	qosFlowIdentifier					QoSFlowIdentifier,
	pduSessionLevelUPactivityreport		UserPlaneTrafficActivityReport,
	iE-Extensions						ProtocolExtensionContainer { {QoSFlowsActivityNotifyItem-ExtIEs} } OPTIONAL,
	...
}

QoSFlowsActivityNotifyItem-ExtIEs XNAP-PROTOCOL-EXTENSION ::= {
	...
}

-- **************************************************************
--
-- XN SETUP REQUEST
--
-- **************************************************************

XnSetupRequest ::= SEQUENCE {
	protocolIEs			ProtocolIE-Container	{{ XnSetupRequest-IEs}},
	...
}

XnSetupRequest-IEs XNAP-PROTOCOL-IES ::= {
	{ ID id-GlobalNG-RAN-node-ID				CRITICALITY reject	TYPE GlobalNG-RANNode-ID						PRESENCE mandatory}|
	{ ID id-TAISupport-list						CRITICALITY reject	TYPE TAISupport-List							PRESENCE mandatory}|
	{ ID id-AMF-Region-Information				CRITICALITY reject	TYPE AMF-Region-Information						PRESENCE mandatory}|
	{ ID id-List-of-served-cells-NR				CRITICALITY reject	TYPE ServedCells-NR								PRESENCE optional }|
	{ ID id-List-of-served-cells-E-UTRA			CRITICALITY reject	TYPE ServedCells-E-UTRA							PRESENCE optional }|
	{ ID id-InterfaceInstanceIndication			CRITICALITY reject	TYPE InterfaceInstanceIndication				PRESENCE optional }|
	{ ID id-TNLConfigurationInfo				CRITICALITY ignore	TYPE TNLConfigurationInfo						PRESENCE optional }|
	{ ID id-PartialListIndicator-NR				CRITICALITY ignore	TYPE PartialListIndicator						PRESENCE optional }|
	{ ID id-CellAndCapacityAssistanceInfo-NR 	CRITICALITY ignore 	TYPE CellAndCapacityAssistanceInfo-NR		PRESENCE optional }|
	{ ID id-PartialListIndicator-EUTRA			CRITICALITY ignore	TYPE PartialListIndicator						PRESENCE optional }|
	{ ID id-CellAndCapacityAssistanceInfo-EUTRA	CRITICALITY ignore 	TYPE CellAndCapacityAssistanceInfo-EUTRA	PRESENCE optional }|
	{ ID id-Local-NG-RAN-Node-Identifier		CRITICALITY ignore	TYPE Local-NG-RAN-Node-Identifier			PRESENCE optional	}|
	{ ID id-Neighbour-NG-RAN-Node-List			CRITICALITY ignore	TYPE Neighbour-NG-RAN-Node-List				PRESENCE optional	},
	...
}

-- **************************************************************
--
-- XN SETUP RESPONSE
--
-- **************************************************************

XnSetupResponse ::= SEQUENCE {
	protocolIEs			ProtocolIE-Container	{{ XnSetupResponse-IEs}},
	...
}

XnSetupResponse-IEs XNAP-PROTOCOL-IES ::= {
	{ ID id-GlobalNG-RAN-node-ID				CRITICALITY reject	TYPE GlobalNG-RANNode-ID						PRESENCE mandatory}|
	{ ID id-TAISupport-list						CRITICALITY reject	TYPE TAISupport-List							PRESENCE mandatory}|
	{ ID id-List-of-served-cells-NR				CRITICALITY reject	TYPE ServedCells-NR								PRESENCE optional }|
	{ ID id-List-of-served-cells-E-UTRA			CRITICALITY reject	TYPE ServedCells-E-UTRA							PRESENCE optional }|
	{ ID id-CriticalityDiagnostics				CRITICALITY ignore	TYPE CriticalityDiagnostics						PRESENCE optional }|
	{ ID id-AMF-Region-Information				CRITICALITY reject	TYPE AMF-Region-Information						PRESENCE optional }|
	{ ID id-InterfaceInstanceIndication			CRITICALITY reject	TYPE InterfaceInstanceIndication				PRESENCE optional }|
	{ ID id-TNLConfigurationInfo				CRITICALITY ignore	TYPE TNLConfigurationInfo						PRESENCE optional	}|
	{ ID id-PartialListIndicator-NR				CRITICALITY ignore	TYPE PartialListIndicator						PRESENCE optional }|
	{ ID id-CellAndCapacityAssistanceInfo-NR 	CRITICALITY ignore 	TYPE CellAndCapacityAssistanceInfo-NR		PRESENCE optional }|
	{ ID id-PartialListIndicator-EUTRA			CRITICALITY ignore	TYPE PartialListIndicator						PRESENCE optional }|
	{ ID id-CellAndCapacityAssistanceInfo-EUTRA	CRITICALITY ignore 	TYPE CellAndCapacityAssistanceInfo-EUTRA	PRESENCE optional }|
	{ ID id-Local-NG-RAN-Node-Identifier		CRITICALITY ignore	TYPE Local-NG-RAN-Node-Identifier			PRESENCE optional	}|
	{ ID id-Neighbour-NG-RAN-Node-List			CRITICALITY ignore	TYPE Neighbour-NG-RAN-Node-List				PRESENCE optional	},
	...
}

-- **************************************************************
--
-- XN SETUP FAILURE
--
-- **************************************************************

XnSetupFailure ::= SEQUENCE {
	protocolIEs			ProtocolIE-Container	{{ XnSetupFailure-IEs}},
	...
}

XnSetupFailure-IEs XNAP-PROTOCOL-IES ::= {
	{ ID id-Cause						CRITICALITY ignore	TYPE Cause							PRESENCE mandatory}|
	{ ID id-TimeToWait					CRITICALITY ignore	TYPE TimeToWait						PRESENCE optional }|
	{ ID id-CriticalityDiagnostics		CRITICALITY ignore	TYPE CriticalityDiagnostics			PRESENCE optional }|
	{ ID id-InterfaceInstanceIndication	CRITICALITY reject	TYPE InterfaceInstanceIndication	PRESENCE optional }|
	{ ID id-MessageOversizeNotification	CRITICALITY ignore	TYPE MessageOversizeNotification	PRESENCE optional },
	...
}

-- **************************************************************
--
-- NG-RAN NODE CONFIGURATION UPDATE
--
-- **************************************************************

NGRANNodeConfigurationUpdate ::= SEQUENCE {
	protocolIEs			ProtocolIE-Container	{{ NGRANNodeConfigurationUpdate-IEs}},
	...
}

NGRANNodeConfigurationUpdate-IEs XNAP-PROTOCOL-IES ::= {
	{ ID id-TAISupport-list							CRITICALITY reject	TYPE TAISupport-List									PRESENCE optional }|
	{ ID id-ConfigurationUpdateInitiatingNodeChoice	CRITICALITY ignore	TYPE ConfigurationUpdateInitiatingNodeChoice	PRESENCE mandatory}|
	{ ID id-TNLA-To-Add-List						CRITICALITY ignore	TYPE TNLA-To-Add-List									PRESENCE optional }|
	{ ID id-TNLA-To-Remove-List						CRITICALITY ignore	TYPE TNLA-To-Remove-List								PRESENCE optional }|
	{ ID id-TNLA-To-Update-List						CRITICALITY ignore	TYPE TNLA-To-Update-List								PRESENCE optional }|
	{ ID id-GlobalNG-RAN-node-ID					CRITICALITY reject	TYPE GlobalNG-RANNode-ID								PRESENCE optional }|
	{ ID id-AMF-Region-Information-To-Add			CRITICALITY reject	TYPE AMF-Region-Information							PRESENCE optional }|
	{ ID id-AMF-Region-Information-To-Delete		CRITICALITY reject	TYPE AMF-Region-Information							PRESENCE optional }|
	{ ID id-InterfaceInstanceIndication				CRITICALITY reject	TYPE InterfaceInstanceIndication					PRESENCE optional }|
	{ ID id-TNLConfigurationInfo					CRITICALITY ignore	TYPE TNLConfigurationInfo								PRESENCE optional	}|
	{ ID id-Coverage-Modification-List				CRITICALITY reject	TYPE Coverage-Modification-List						PRESENCE optional	}|
	{ ID id-Local-NG-RAN-Node-Identifier			CRITICALITY ignore	TYPE Local-NG-RAN-Node-Identifier					PRESENCE optional	}|
	{ ID id-Neighbour-NG-RAN-Node-List				CRITICALITY ignore	TYPE Neighbour-NG-RAN-Node-List						PRESENCE optional	}|
	{ ID id-Local-NG-RAN-Node-Identifier-Removal	CRITICALITY ignore	TYPE Local-NG-RAN-Node-Identifier					PRESENCE optional	},
	...
}

ConfigurationUpdateInitiatingNodeChoice ::= CHOICE {
	gNB									ProtocolIE-Container	{ {ConfigurationUpdate-gNB} },
	ng-eNB								ProtocolIE-Container	{ {ConfigurationUpdate-ng-eNB} },
	choice-extension					ProtocolIE-Single-Container { {ServedCellsToUpdateInitiatingNodeChoice-ExtIEs} }
}

ServedCellsToUpdateInitiatingNodeChoice-ExtIEs XNAP-PROTOCOL-IES ::= {
	...
}

ConfigurationUpdate-gNB XNAP-PROTOCOL-IES ::= {
	{ ID id-servedCellsToUpdate-NR			CRITICALITY ignore TYPE	ServedCellsToUpdate-NR							PRESENCE optional }|
	{ ID id-cellAssistanceInfo-NR			CRITICALITY ignore TYPE	CellAssistanceInfo-NR							PRESENCE optional }|
	{ ID id-cellAssistanceInfo-EUTRA		CRITICALITY ignore TYPE	CellAssistanceInfo-EUTRA						PRESENCE optional }|
	{ ID id-ServedCellSpecificInfoReq-NR	CRITICALITY ignore TYPE	ServedCellSpecificInfoReq-NR					PRESENCE optional},
	...
}


ConfigurationUpdate-ng-eNB XNAP-PROTOCOL-IES ::= {
	{ ID id-servedCellsToUpdate-E-UTRA	CRITICALITY ignore TYPE	ServedCellsToUpdate-E-UTRA				PRESENCE optional }|
	{ ID id-cellAssistanceInfo-NR		CRITICALITY ignore TYPE	CellAssistanceInfo-NR			PRESENCE optional }|
	{ ID id-cellAssistanceInfo-EUTRA			CRITICALITY ignore TYPE	CellAssistanceInfo-EUTRA					PRESENCE optional },
		...
}



-- **************************************************************
--
-- NG-RAN NODE CONFIGURATION UPDATE ACKNOWLEDGE
--
-- **************************************************************

NGRANNodeConfigurationUpdateAcknowledge ::= SEQUENCE {
	protocolIEs			ProtocolIE-Container	{{ NGRANNodeConfigurationUpdateAcknowledge-IEs}},
	...
}

NGRANNodeConfigurationUpdateAcknowledge-IEs XNAP-PROTOCOL-IES ::= {
	{ ID id-RespondingNodeTypeConfigUpdateAck			CRITICALITY ignore	TYPE RespondingNodeTypeConfigUpdateAck		PRESENCE mandatory}|
	{ ID id-TNLA-Setup-List								CRITICALITY ignore	TYPE TNLA-Setup-List								PRESENCE optional }|
	{ ID id-TNLA-Failed-To-Setup-List					CRITICALITY ignore	TYPE TNLA-Failed-To-Setup-List					PRESENCE optional }|
	{ ID id-CriticalityDiagnostics						CRITICALITY ignore	TYPE CriticalityDiagnostics						PRESENCE optional }|
	{ ID id-InterfaceInstanceIndication					CRITICALITY reject	TYPE InterfaceInstanceIndication				PRESENCE optional }|
	{ ID id-TNLConfigurationInfo						CRITICALITY ignore	TYPE TNLConfigurationInfo						PRESENCE optional	}|
	{ ID id-Local-NG-RAN-Node-Identifier				CRITICALITY ignore	TYPE Local-NG-RAN-Node-Identifier				PRESENCE optional	}|
	{ ID id-Neighbour-NG-RAN-Node-List					CRITICALITY ignore	TYPE Neighbour-NG-RAN-Node-List				PRESENCE optional	}|
	{ ID id-Local-NG-RAN-Node-Identifier-Removal		CRITICALITY ignore	TYPE Local-NG-RAN-Node-Identifier				PRESENCE optional	},
	...
}
RespondingNodeTypeConfigUpdateAck ::= CHOICE {
	ng-eNB					RespondingNodeTypeConfigUpdateAck-ng-eNB,
	gNB						RespondingNodeTypeConfigUpdateAck-gNB,
	choice-extension		ProtocolIE-Single-Container { {RespondingNodeTypeConfigUpdateAck-ExtIEs} }
}

RespondingNodeTypeConfigUpdateAck-ExtIEs XNAP-PROTOCOL-IES ::= {
	...
}

RespondingNodeTypeConfigUpdateAck-ng-eNB ::= SEQUENCE {
	iE-Extension		ProtocolExtensionContainer { {RespondingNodeTypeConfigUpdateAck-ng-eNB-ExtIEs} }	OPTIONAL,
	...
}

RespondingNodeTypeConfigUpdateAck-ng-eNB-ExtIEs XNAP-PROTOCOL-EXTENSION ::= {
	{ ID id-List-of-served-cells-E-UTRA				CRITICALITY ignore	EXTENSION ServedCells-E-UTRA							PRESENCE optional }|
	{ ID id-PartialListIndicator-EUTRA				CRITICALITY ignore	EXTENSION PartialListIndicator						PRESENCE optional }|
	{ ID id-CellAndCapacityAssistanceInfo-EUTRA		CRITICALITY ignore	EXTENSION CellAndCapacityAssistanceInfo-EUTRA	PRESENCE optional },
	...
}


RespondingNodeTypeConfigUpdateAck-gNB ::= SEQUENCE {
	served-NR-Cells		ServedCells-NR																OPTIONAL,
	iE-Extension		ProtocolExtensionContainer { {RespondingNodeTypeConfigUpdateAck-gNB-ExtIEs} }	OPTIONAL,
	...
}

RespondingNodeTypeConfigUpdateAck-gNB-ExtIEs XNAP-PROTOCOL-EXTENSION ::= {
	{ ID id-PartialListIndicator-NR				CRITICALITY ignore	EXTENSION PartialListIndicator						PRESENCE optional }|
	{ ID id-CellAndCapacityAssistanceInfo-NR 	CRITICALITY ignore 	EXTENSION CellAndCapacityAssistanceInfo-NR		PRESENCE optional },
	...
}


-- **************************************************************
--
-- NG-RAN NODE CONFIGURATION UPDATE FAILURE
--
-- **************************************************************

NGRANNodeConfigurationUpdateFailure ::= SEQUENCE {
	protocolIEs			ProtocolIE-Container	{{NGRANNodeConfigurationUpdateFailure-IEs}},
	...
}

NGRANNodeConfigurationUpdateFailure-IEs XNAP-PROTOCOL-IES ::= {
	{ ID id-Cause						CRITICALITY ignore	TYPE Cause							PRESENCE mandatory}|
	{ ID id-TimeToWait					CRITICALITY ignore	TYPE TimeToWait						PRESENCE optional }|
	{ ID id-CriticalityDiagnostics		CRITICALITY ignore	TYPE CriticalityDiagnostics			PRESENCE optional }|
	{ ID id-InterfaceInstanceIndication	CRITICALITY reject	TYPE InterfaceInstanceIndication	PRESENCE optional },
	...
}


-- **************************************************************
--
-- E-UTRA NR CELL RESOURCE COORDINATION REQUEST
--
-- **************************************************************

E-UTRA-NR-CellResourceCoordinationRequest ::= SEQUENCE {
	protocolIEs			ProtocolIE-Container	{{E-UTRA-NR-CellResourceCoordinationRequest-IEs}},
	...
}

E-UTRA-NR-CellResourceCoordinationRequest-IEs XNAP-PROTOCOL-IES ::= {
	{ ID id-initiatingNodeType-ResourceCoordRequest	CRITICALITY reject	TYPE InitiatingNodeType-ResourceCoordRequest		PRESENCE mandatory}|
	{ ID id-InterfaceInstanceIndication				CRITICALITY reject	TYPE InterfaceInstanceIndication						PRESENCE optional },
	...
}

InitiatingNodeType-ResourceCoordRequest ::= CHOICE {
	ng-eNB								ResourceCoordRequest-ng-eNB-initiated,
	gNB									ResourceCoordRequest-gNB-initiated,
	choice-extension					ProtocolIE-Single-Container { {InitiatingNodeType-ResourceCoordRequest-ExtIEs} }
}

InitiatingNodeType-ResourceCoordRequest-ExtIEs XNAP-PROTOCOL-IES ::= {
	...
}

ResourceCoordRequest-ng-eNB-initiated ::= SEQUENCE {
	dataTrafficResourceIndication		DataTrafficResourceIndication,
	spectrumSharingGroupID				SpectrumSharingGroupID,
	listofE-UTRACells					SEQUENCE (SIZE(1.. maxnoofCellsinNG-RANnode)) OF E-UTRA-CGI							OPTIONAL,
	iE-Extensions						ProtocolExtensionContainer { {ResourceCoordRequest-ng-eNB-initiated-ExtIEs} }	OPTIONAL,
	...
}

ResourceCoordRequest-ng-eNB-initiated-ExtIEs XNAP-PROTOCOL-EXTENSION ::= {
	...
}


ResourceCoordRequest-gNB-initiated ::= SEQUENCE {
	dataTrafficResourceIndication		DataTrafficResourceIndication,
	listofE-UTRACells					SEQUENCE (SIZE(1.. maxnoofCellsinNG-RANnode)) OF E-UTRA-CGI						OPTIONAL,
	spectrumSharingGroupID				SpectrumSharingGroupID,
	listofNRCells						SEQUENCE (SIZE(1.. maxnoofCellsinNG-RANnode)) OF NR-CGI								OPTIONAL,
	iE-Extensions						ProtocolExtensionContainer { {ResourceCoordRequest-gNB-initiated-ExtIEs} }	OPTIONAL,
	...
}

ResourceCoordRequest-gNB-initiated-ExtIEs XNAP-PROTOCOL-EXTENSION ::= {
	...
}


-- **************************************************************
--
-- E-UTRA NR CELL RESOURCE COORDINATION RESPONSE
--
-- **************************************************************

E-UTRA-NR-CellResourceCoordinationResponse::= SEQUENCE {
	protocolIEs			ProtocolIE-Container	{{E-UTRA-NR-CellResourceCoordinationResponse-IEs}},
	...
}

E-UTRA-NR-CellResourceCoordinationResponse-IEs XNAP-PROTOCOL-IES ::= {
	{ ID id-respondingNodeType-ResourceCoordResponse  	CRITICALITY reject	TYPE RespondingNodeType-ResourceCoordResponse 	PRESENCE mandatory}|
	{ ID id-InterfaceInstanceIndication					CRITICALITY reject	TYPE InterfaceInstanceIndication						PRESENCE optional },
	...
}

RespondingNodeType-ResourceCoordResponse ::= CHOICE {
	ng-eNB								ResourceCoordResponse-ng-eNB-initiated,
	gNB									ResourceCoordResponse-gNB-initiated,
	choice-extension					ProtocolIE-Single-Container { {RespondingNodeType-ResourceCoordResponse-ExtIEs} }
}

RespondingNodeType-ResourceCoordResponse-ExtIEs XNAP-PROTOCOL-IES ::= {
	...
}

ResourceCoordResponse-ng-eNB-initiated ::= SEQUENCE {
	dataTrafficResourceIndication		DataTrafficResourceIndication,
	spectrumSharingGroupID				SpectrumSharingGroupID,
	listofE-UTRACells					SEQUENCE (SIZE(1.. maxnoofCellsinNG-RANnode)) OF E-UTRA-CGI								OPTIONAL,
	iE-Extensions						ProtocolExtensionContainer { {ResourceCoordResponse-ng-eNB-initiated-ExtIEs} }		OPTIONAL,
	...
}

ResourceCoordResponse-ng-eNB-initiated-ExtIEs XNAP-PROTOCOL-EXTENSION ::= {
	...
}


ResourceCoordResponse-gNB-initiated ::= SEQUENCE {
	dataTrafficResourceIndication		DataTrafficResourceIndication,
	spectrumSharingGroupID				SpectrumSharingGroupID,
	listofNRCells						SEQUENCE (SIZE(1.. maxnoofCellsinNG-RANnode)) OF NR-CGI									OPTIONAL,
	iE-Extensions						ProtocolExtensionContainer { {ResourceCoordResponse-gNB-initiated-ExtIEs} }		OPTIONAL,
	...
}

ResourceCoordResponse-gNB-initiated-ExtIEs XNAP-PROTOCOL-EXTENSION ::= {
	...
}

-- **************************************************************
--
-- SECONDARY RAT DATA USAGE REPORT
--
-- **************************************************************

SecondaryRATDataUsageReport ::= SEQUENCE {
	protocolIEs		ProtocolIE-Container		{{SecondaryRATDataUsageReport-IEs}},
	...
}

SecondaryRATDataUsageReport-IEs XNAP-PROTOCOL-IES ::= {
	{ ID id-M-NG-RANnodeUEXnAPID					CRITICALITY reject		TYPE NG-RANnodeUEXnAPID								PRESENCE mandatory}|
	{ ID id-S-NG-RANnodeUEXnAPID					CRITICALITY reject		TYPE NG-RANnodeUEXnAPID								PRESENCE mandatory}|
	{ ID id-PDUSessionResourceSecondaryRATUsageList	CRITICALITY reject		TYPE PDUSessionResourceSecondaryRATUsageList	PRESENCE mandatory},
	...
}


-- **************************************************************
--
-- XN REMOVAL REQUEST
--
-- **************************************************************

XnRemovalRequest ::= SEQUENCE {
	protocolIEs			ProtocolIE-Container	{{ XnRemovalRequest-IEs}},
	...
}

XnRemovalRequest-IEs XNAP-PROTOCOL-IES ::= {
	{ ID id-GlobalNG-RAN-node-ID		CRITICALITY reject	TYPE GlobalNG-RANNode-ID			PRESENCE mandatory}|
	{ ID id-XnRemovalThreshold			CRITICALITY reject	TYPE XnBenefitValue					PRESENCE optional }|
	{ ID id-InterfaceInstanceIndication	CRITICALITY reject	TYPE InterfaceInstanceIndication	PRESENCE optional },
	...
}

-- **************************************************************
--
-- XN REMOVAL RESPONSE
--
-- **************************************************************

XnRemovalResponse ::= SEQUENCE {
	protocolIEs			ProtocolIE-Container	{{ XnRemovalResponse-IEs}},
	...
}

XnRemovalResponse-IEs XNAP-PROTOCOL-IES ::= {
	{ ID id-GlobalNG-RAN-node-ID		CRITICALITY reject	TYPE GlobalNG-RANNode-ID			PRESENCE mandatory}|
	{ ID id-CriticalityDiagnostics		CRITICALITY ignore	TYPE CriticalityDiagnostics			PRESENCE optional }|
	{ ID id-InterfaceInstanceIndication	CRITICALITY reject	TYPE InterfaceInstanceIndication	PRESENCE optional },
	...
}

-- **************************************************************
--
-- XN REMOVAL FAILURE
--
-- **************************************************************

XnRemovalFailure ::= SEQUENCE {
	protocolIEs			ProtocolIE-Container	{{ XnRemovalFailure-IEs}},
	...
}

XnRemovalFailure-IEs XNAP-PROTOCOL-IES ::= {
	{ ID id-Cause						CRITICALITY ignore	TYPE Cause							PRESENCE mandatory}|
	{ ID id-CriticalityDiagnostics		CRITICALITY ignore	TYPE CriticalityDiagnostics			PRESENCE optional }|
	{ ID id-InterfaceInstanceIndication	CRITICALITY reject	TYPE InterfaceInstanceIndication	PRESENCE optional },
	...
}

-- **************************************************************
--
-- CELL ACTIVATION REQUEST
--
-- **************************************************************

CellActivationRequest ::= SEQUENCE {
	protocolIEs			ProtocolIE-Container	{{ CellActivationRequest-IEs}},
	...
}

CellActivationRequest-IEs XNAP-PROTOCOL-IES ::= {
	{ ID id-ServedCellsToActivate					CRITICALITY reject		TYPE ServedCellsToActivate						PRESENCE mandatory}|
	{ ID id-ActivationIDforCellActivation			CRITICALITY reject		TYPE ActivationIDforCellActivation			PRESENCE mandatory}|
	{ ID id-InterfaceInstanceIndication				CRITICALITY reject		TYPE InterfaceInstanceIndication				PRESENCE optional },
	...
}

ServedCellsToActivate ::= CHOICE {
	nr-cells							SEQUENCE (SIZE(1..maxnoofCellsinNG-RANnode)) OF NR-CGI,
	e-utra-cells						SEQUENCE (SIZE(1..maxnoofCellsinNG-RANnode)) OF E-UTRA-CGI,
	choice-extension					ProtocolIE-Single-Container { {ServedCellsToActivate-ExtIEs} }
}

ServedCellsToActivate-ExtIEs XNAP-PROTOCOL-IES ::= {
	...
}


-- **************************************************************
--
-- CELL ACTIVATION RESPONSE
--
-- **************************************************************

CellActivationResponse ::= SEQUENCE {
	protocolIEs			ProtocolIE-Container	{{CellActivationResponse-IEs}},
	...
}

CellActivationResponse-IEs XNAP-PROTOCOL-IES ::= {
	{ ID id-ActivatedServedCells					CRITICALITY reject		TYPE ActivatedServedCells						PRESENCE mandatory}|
	{ ID id-ActivationIDforCellActivation			CRITICALITY reject		TYPE ActivationIDforCellActivation			PRESENCE mandatory}|
	{ ID id-CriticalityDiagnostics					CRITICALITY ignore		TYPE CriticalityDiagnostics						PRESENCE optional }|
	{ ID id-InterfaceInstanceIndication				CRITICALITY reject		TYPE InterfaceInstanceIndication				PRESENCE optional },
	...
}

ActivatedServedCells ::= CHOICE {
	nr-cells							SEQUENCE (SIZE(1..maxnoofCellsinNG-RANnode)) OF NR-CGI,
	e-utra-cells						SEQUENCE (SIZE(1..maxnoofCellsinNG-RANnode)) OF E-UTRA-CGI,
	choice-extension					ProtocolIE-Single-Container { {ActivatedServedCells-ExtIEs} }
}

ActivatedServedCells-ExtIEs XNAP-PROTOCOL-IES ::= {
	...
}


-- **************************************************************
--
-- CELL ACTIVATION FAILURE
--
-- **************************************************************

CellActivationFailure ::= SEQUENCE {
	protocolIEs			ProtocolIE-Container	{{CellActivationFailure-IEs}},
	...
}

CellActivationFailure-IEs XNAP-PROTOCOL-IES ::= {
	{ ID id-ActivationIDforCellActivation			CRITICALITY reject		TYPE ActivationIDforCellActivation			PRESENCE mandatory}|
	{ ID id-Cause									CRITICALITY ignore		TYPE Cause											PRESENCE mandatory}|
	{ ID id-CriticalityDiagnostics					CRITICALITY ignore		TYPE CriticalityDiagnostics						PRESENCE optional }|
	{ ID id-InterfaceInstanceIndication				CRITICALITY reject		TYPE InterfaceInstanceIndication				PRESENCE optional },
	...
}

-- **************************************************************
--
-- RESET REQUEST
--
-- **************************************************************

ResetRequest ::= SEQUENCE {
	protocolIEs			ProtocolIE-Container	{{ResetRequest-IEs}},
	...
}

ResetRequest-IEs XNAP-PROTOCOL-IES ::= {
	{ ID id-ResetRequestTypeInfo					CRITICALITY reject		TYPE ResetRequestTypeInfo						PRESENCE mandatory}|
	{ ID id-Cause									CRITICALITY ignore		TYPE Cause											PRESENCE mandatory}|
	{ ID id-InterfaceInstanceIndication				CRITICALITY reject		TYPE InterfaceInstanceIndication				PRESENCE optional },
	...
}

-- **************************************************************
--
-- RESET RESPONSE
--
-- **************************************************************

ResetResponse ::= SEQUENCE {
	protocolIEs			ProtocolIE-Container	{{ResetResponse-IEs}},
	...
}

ResetResponse-IEs XNAP-PROTOCOL-IES ::= {
	{ ID id-ResetResponseTypeInfo					CRITICALITY reject		TYPE ResetResponseTypeInfo						PRESENCE mandatory}|
	{ ID id-CriticalityDiagnostics					CRITICALITY ignore		TYPE CriticalityDiagnostics						PRESENCE optional }|
	{ ID id-InterfaceInstanceIndication				CRITICALITY reject		TYPE InterfaceInstanceIndication				PRESENCE optional },
	...
}

-- **************************************************************
--
-- ERROR INDICATION
--
-- **************************************************************

ErrorIndication ::= SEQUENCE {
	protocolIEs			ProtocolIE-Container	{{ErrorIndication-IEs}},
	...
}

ErrorIndication-IEs XNAP-PROTOCOL-IES ::= {
	{ ID id-oldNG-RANnodeUEXnAPID					CRITICALITY ignore		TYPE NG-RANnodeUEXnAPID							PRESENCE optional }|
	{ ID id-newNG-RANnodeUEXnAPID					CRITICALITY ignore		TYPE NG-RANnodeUEXnAPID							PRESENCE optional }|
	{ ID id-Cause									CRITICALITY ignore		TYPE Cause											PRESENCE optional }|
	{ ID id-CriticalityDiagnostics					CRITICALITY ignore		TYPE CriticalityDiagnostics						PRESENCE optional }|
	{ ID id-InterfaceInstanceIndication				CRITICALITY reject		TYPE InterfaceInstanceIndication				PRESENCE optional },
	...
}

-- **************************************************************
--
-- PRIVATE MESSAGE
--
-- **************************************************************

PrivateMessage ::= SEQUENCE {
	privateIEs		PrivateIE-Container	{{PrivateMessage-IEs}},
	...
}

PrivateMessage-IEs XNAP-PRIVATE-IES ::= {
	...
}


-- **************************************************************
--
-- TRACE START
--
-- **************************************************************

TraceStart ::= SEQUENCE {
	protocolIEs		ProtocolIE-Container		{ {TraceStartIEs} },
	...
}

TraceStartIEs XNAP-PROTOCOL-IES ::= {
	{ ID id-M-NG-RANnodeUEXnAPID					CRITICALITY reject	TYPE NG-RANnodeUEXnAPID							PRESENCE mandatory}|
	{ ID id-S-NG-RANnodeUEXnAPID					CRITICALITY reject	TYPE NG-RANnodeUEXnAPID							PRESENCE mandatory}|
	{ ID id-TraceActivation							CRITICALITY ignore	TYPE TraceActivation							PRESENCE optional },
	...
}

-- **************************************************************
--
-- DEACTIVATE TRACE
--
-- **************************************************************

DeactivateTrace ::= SEQUENCE {
	protocolIEs		ProtocolIE-Container		{ {DeactivateTraceIEs} },
	...
}

DeactivateTraceIEs XNAP-PROTOCOL-IES ::= {
	{ ID id-M-NG-RANnodeUEXnAPID					CRITICALITY reject	TYPE NG-RANnodeUEXnAPID							PRESENCE mandatory}|
	{ ID id-S-NG-RANnodeUEXnAPID					CRITICALITY reject	TYPE NG-RANnodeUEXnAPID							PRESENCE mandatory}|
	{ ID id-NG-RANTraceID							CRITICALITY ignore	TYPE NG-RANTraceID								PRESENCE mandatory},
	...
}

-- **************************************************************
--
-- FAILURE INDICATION
--
-- **************************************************************

FailureIndication ::= SEQUENCE {
	protocolIEs			ProtocolIE-Container	{{FailureIndication-IEs}},
	...
}

FailureIndication-IEs XNAP-PROTOCOL-IES ::= {
	{ ID id-InitiatingCondition-FailureIndication				CRITICALITY reject		TYPE InitiatingCondition-FailureIndication							PRESENCE mandatory},
	...
}

-- **************************************************************
--
-- HANDOVER REPORT
--
-- **************************************************************

HandoverReport ::= SEQUENCE {
	protocolIEs			ProtocolIE-Container	{{ HandoverReport-IEs}},
	...
}

HandoverReport-IEs XNAP-PROTOCOL-IES ::= {
	{ ID id-HandoverReportType			CRITICALITY ignore		TYPE HandoverReportType				PRESENCE mandatory}|
	{ ID id-HandoverCause				CRITICALITY ignore		TYPE Cause							PRESENCE mandatory}|
	{ ID id-SourceCellCGI				CRITICALITY ignore		TYPE GlobalNG-RANCell-ID			PRESENCE mandatory }|
	{ ID id-TargetCellCGI				CRITICALITY ignore		TYPE GlobalNG-RANCell-ID			PRESENCE mandatory }|
	{ ID id-ReEstablishmentCellCGI		CRITICALITY ignore		TYPE GlobalCell-ID					PRESENCE conditional }|
-- This IE shall be present if the Handover Report Type IE is set to the value "HO to wrong cell"
	{ ID id-TargetCellinEUTRAN   		CRITICALITY ignore		TYPE TargetCellinEUTRAN				PRESENCE conditional }|
-- This IE shall be present if the Handover Report Type IE is set to the value "Inter-system ping-pong"
	{ ID id-SourceCellCRNTI				CRITICALITY ignore		TYPE C-RNTI							PRESENCE optional }|
	{ ID id-MobilityInformation			CRITICALITY ignore		TYPE MobilityInformation			PRESENCE optional }|
	{ ID id-UERLFReportContainer		CRITICALITY ignore		TYPE UERLFReportContainer			PRESENCE optional }|
	{ ID id-CHOConfiguration			CRITICALITY ignore		TYPE CHOConfiguration				PRESENCE optional},
	...
}

-- **************************************************************
--
-- RESOURCE STATUS REQUEST
--
-- **************************************************************

ResourceStatusRequest ::= SEQUENCE {
	protocolIEs		ProtocolIE-Container	{{ResourceStatusRequest-IEs}},
	...
}

ResourceStatusRequest-IEs XNAP-PROTOCOL-IES ::= {
	{ ID id-NGRAN-Node1-Measurement-ID			CRITICALITY reject	TYPE Measurement-ID					PRESENCE mandatory}|
	{ ID id-NGRAN-Node2-Measurement-ID			CRITICALITY ignore	TYPE Measurement-ID					PRESENCE conditional}|
-- This IE shall be present if the Registration Request IE is set to the value "stop" or "add".
	{ ID id-RegistrationRequest					CRITICALITY reject	TYPE RegistrationRequest			PRESENCE mandatory}|
	{ ID id-ReportCharacteristics				CRITICALITY reject	TYPE ReportCharacteristics			PRESENCE conditional}|
-- This IE shall be present if the Registration Request IE is set to the value "start".
	{ ID id-CellToReport						CRITICALITY ignore	TYPE CellToReport					PRESENCE optional}|
	{ ID id-ReportingPeriodicity				CRITICALITY ignore	TYPE ReportingPeriodicity			PRESENCE optional},
	...
}


-- **************************************************************
--
-- RESOURCE STATUS RESPONSE
--
-- **************************************************************

ResourceStatusResponse ::= SEQUENCE {
	protocolIEs		ProtocolIE-Container	{{ResourceStatusResponse-IEs}},
	...
}

ResourceStatusResponse-IEs XNAP-PROTOCOL-IES ::= {
	{ ID id-NGRAN-Node1-Measurement-ID			CRITICALITY reject	TYPE Measurement-ID							PRESENCE mandatory}|
	{ ID id-NGRAN-Node2-Measurement-ID			CRITICALITY reject	TYPE Measurement-ID							PRESENCE mandatory}|
	{ ID id-CriticalityDiagnostics				CRITICALITY ignore	TYPE CriticalityDiagnostics					PRESENCE optional},
	...
}


-- **************************************************************
--
-- RESOURCE STATUS FAILURE
--
-- **************************************************************

ResourceStatusFailure ::= SEQUENCE {
	protocolIEs		ProtocolIE-Container	{{ResourceStatusFailure-IEs}},
	...
}

ResourceStatusFailure-IEs XNAP-PROTOCOL-IES ::= {
	{ ID id-NGRAN-Node1-Measurement-ID				CRITICALITY reject	TYPE Measurement-ID									PRESENCE mandatory}|
	{ ID id-NGRAN-Node2-Measurement-ID				CRITICALITY reject	TYPE Measurement-ID									PRESENCE mandatory}|
	{ ID id-Cause									CRITICALITY ignore	TYPE Cause											PRESENCE mandatory}|
	{ ID id-CriticalityDiagnostics					CRITICALITY ignore	TYPE CriticalityDiagnostics						PRESENCE optional},
	...
}


-- **************************************************************
--
-- RESOURCE STATUS UPDATE
--
-- **************************************************************

ResourceStatusUpdate ::= SEQUENCE {
	protocolIEs		ProtocolIE-Container	{{ResourceStatusUpdate-IEs}},
	...
}

ResourceStatusUpdate-IEs XNAP-PROTOCOL-IES ::= {
	{ ID id-NGRAN-Node1-Measurement-ID		CRITICALITY reject	TYPE Measurement-ID					PRESENCE mandatory}|
	{ ID id-NGRAN-Node2-Measurement-ID		CRITICALITY reject	TYPE Measurement-ID					PRESENCE mandatory}|
{ ID id-CellMeasurementResult			CRITICALITY ignore	TYPE CellMeasurementResult			PRESENCE mandatory},
	...
}

-- **************************************************************
--
-- MOBILITY CHANGE REQUEST
--
-- **************************************************************

MobilityChangeRequest ::= SEQUENCE {
	protocolIEs		ProtocolIE-Container	{{MobilityChangeRequest-IEs}},
	...
}

MobilityChangeRequest-IEs XNAP-PROTOCOL-IES ::= {
	{ ID id-NG-RANnode1CellID						CRITICALITY reject	TYPE GlobalNG-RANCell-ID							PRESENCE mandatory}|
	{ ID id-NG-RANnode2CellID							CRITICALITY reject	TYPE GlobalNG-RANCell-ID							PRESENCE mandatory}|
	{ ID id-NG-RANnode1MobilityParameters				CRITICALITY reject	TYPE MobilityParametersInformation				PRESENCE optional}|
	{ ID id-NG-RANnode2ProposedMobilityParameters	CRITICALITY reject	TYPE MobilityParametersInformation				PRESENCE optional}|
	{ ID id-Cause										CRITICALITY ignore	TYPE Cause											PRESENCE mandatory}|
	{ ID id-SSBOffsets-List								CRITICALITY ignore	TYPE SSBOffsets-List								PRESENCE optional},
	...
}


-- **************************************************************
--
-- MOBILITY CHANGE ACKNOWLEDGE
--
-- **************************************************************

MobilityChangeAcknowledge ::= SEQUENCE {
	protocolIEs		ProtocolIE-Container	{{MobilityChangeAcknowledge-IEs}},
	...
}

MobilityChangeAcknowledge-IEs XNAP-PROTOCOL-IES ::= {
	{ ID id-NG-RANnode1CellID					CRITICALITY reject	TYPE GlobalNG-RANCell-ID							PRESENCE mandatory}|
	{ ID id-NG-RANnode2CellID					CRITICALITY reject	TYPE GlobalNG-RANCell-ID							PRESENCE mandatory}|
	{ ID id-CriticalityDiagnostics				CRITICALITY ignore	TYPE CriticalityDiagnostics							PRESENCE optional},
	...
}


-- **************************************************************
--
-- MOBILITY CHANGE FAILURE
--
-- **************************************************************

MobilityChangeFailure ::= SEQUENCE {
	protocolIEs		ProtocolIE-Container	{{MobilityChangeFailure-IEs}},
	...
}

MobilityChangeFailure-IEs XNAP-PROTOCOL-IES ::= {
	{ ID id-NG-RANnode1CellID						CRITICALITY reject	TYPE GlobalNG-RANCell-ID									PRESENCE mandatory}|
	{ ID id-NG-RANnode2CellID							CRITICALITY reject	TYPE GlobalNG-RANCell-ID									PRESENCE mandatory}|
	{ ID id-Cause									CRITICALITY ignore	TYPE Cause													PRESENCE mandatory}|
	{ ID id-MobilityParametersModificationRange 	CRITICALITY reject	TYPE MobilityParametersModificationRange				PRESENCE optional}|
	{ ID id-CriticalityDiagnostics					CRITICALITY ignore	TYPE CriticalityDiagnostics								PRESENCE optional}|
	{ ID id-NG-RANnode2SSBOffsetsModificationRange	CRITICALITY ignore	TYPE NG-RANnode2SSBOffsetsModificationRange			PRESENCE optional},
	...
}


-- **************************************************************
--
-- ACCESS AND MOBILITY INDICATION
--
-- **************************************************************

AccessAndMobilityIndication ::= SEQUENCE {
	protocolIEs			ProtocolIE-Container	{{ AccessAndMobilityIndication-IEs}},
	...
}
AccessAndMobilityIndication-IEs XNAP-PROTOCOL-IES ::= {
	{ ID id-RACHReportInformation			CRITICALITY ignore		TYPE RACHReportInformation					PRESENCE optional}|
	{ ID id-SuccessfulHOReportInformation		CRITICALITY ignore		TYPE SuccessfulHOReportInformation			PRESENCE optional},
	...
}

-- **************************************************************
--
-- CELL TRAFFIC TRACE
--
-- **************************************************************

CellTrafficTrace ::= SEQUENCE {
	protocolIEs		ProtocolIE-Container		{ {CellTrafficTraceIEs} },
	...
}

CellTrafficTraceIEs XNAP-PROTOCOL-IES ::= {
	{ ID id-M-NG-RANnodeUEXnAPID			CRITICALITY reject	TYPE NG-RANnodeUEXnAPID				PRESENCE mandatory}|
	{ ID id-S-NG-RANnodeUEXnAPID			CRITICALITY reject	TYPE NG-RANnodeUEXnAPID				PRESENCE mandatory}|
	{ ID id-NG-RANTraceID					CRITICALITY ignore	TYPE NG-RANTraceID				PRESENCE mandatory	}|
	{ ID id-TraceCollectionEntityIPAddress	CRITICALITY ignore	TYPE TransportLayerAddress			PRESENCE mandatory	}|
	{ ID id-PrivacyIndicator				CRITICALITY ignore	TYPE PrivacyIndicator				PRESENCE optional	}|
{ ID id-TraceCollectionEntityURI		CRITICALITY ignore	TYPE URIaddress						PRESENCE optional},
	...
}

-- **************************************************************
--
-- RAN MULTICAST GROUP PAGING
--
-- **************************************************************

RANMulticastGroupPaging ::= SEQUENCE {
	protocolIEs		ProtocolIE-Container	{{RANMulticastGroupPaging-IEs}},
	...
}

RANMulticastGroupPaging-IEs XNAP-PROTOCOL-IES ::= {
	{ ID id-MBS-Session-ID							CRITICALITY reject	TYPE MBS-Session-ID									PRESENCE mandatory}|
	{ ID id-UEIdentityIndexList-MBSGroupPaging			CRITICALITY reject	TYPE UEIdentityIndexList-MBSGroupPaging		PRESENCE mandatory}|
	{ ID id-MulticastRANPagingArea					CRITICALITY reject	TYPE RANPagingArea									PRESENCE mandatory},
	...
}

-- **************************************************************
--
-- SCG FAILURE INFORMATION REPORT
--
-- **************************************************************

ScgFailureInformationReport ::= SEQUENCE {
	protocolIEs			ProtocolIE-Container	{{ ScgFailureInformationReport-IEs}},
	...
}

ScgFailureInformationReport-IEs XNAP-PROTOCOL-IES ::= {
	{ ID id-M-NG-RANnodeUEXnAPID					CRITICALITY ignore		TYPE NG-RANnodeUEXnAPID							PRESENCE mandatory }|
	{ ID id-S-NG-RANnodeUEXnAPID					CRITICALITY ignore		TYPE NG-RANnodeUEXnAPID							PRESENCE mandatory }|
	{ ID id-SourcePSCellCGI								CRITICALITY ignore		TYPE GlobalNG-RANCell-ID							PRESENCE optional }|
	{ ID id-FailedPSCellCGI								CRITICALITY ignore		TYPE GlobalNG-RANCell-ID							PRESENCE optional }|
	{ ID id-SCGFailureReportContainer					CRITICALITY ignore		TYPE SCGFailureReportContainer					PRESENCE mandatory }|
	{ ID id-SNMobilityInformation				CRITICALITY ignore		TYPE SNMobilityInformation						PRESENCE optional },
	...
}

-- **************************************************************
--
-- SCG FAILURE TRANSFER
--
-- **************************************************************

ScgFailureTransfer ::= SEQUENCE {
	protocolIEs			ProtocolIE-Container	{{ ScgFailureTransfer-IEs}},
	...
}
ScgFailureTransfer-IEs XNAP-PROTOCOL-IES ::= {
	{ ID id-M-NG-RANnodeUEXnAPID					CRITICALITY ignore		TYPE NG-RANnodeUEXnAPID							PRESENCE mandatory }|
	{ ID id-S-NG-RANnodeUEXnAPID					CRITICALITY ignore		TYPE NG-RANnodeUEXnAPID							PRESENCE mandatory },
	...
}


-- **************************************************************
--
-- F1-C TRAFFIC TRANSFER

--
-- **************************************************************

F1CTrafficTransfer ::= SEQUENCE {
	protocolIEs		ProtocolIE-Container		{{ F1CTrafficTransfer-IEs}},
	...
}

F1CTrafficTransfer-IEs XNAP-PROTOCOL-IES ::= {
	{ ID id-M-NG-RANnodeUEXnAPID						CRITICALITY reject	TYPE NG-RANnodeUEXnAPID			PRESENCE mandatory}|
	{ ID id-S-NG-RANnodeUEXnAPID						CRITICALITY reject	TYPE NG-RANnodeUEXnAPID			PRESENCE mandatory}|
	{ ID id-F1CTrafficContainer							CRITICALITY reject	TYPE F1CTrafficContainer			PRESENCE mandatory},
	...
}


-- **************************************************************
--
-- IAB TRANSPORT MIGRATION MANAGEMENT REQUEST
--
-- **************************************************************

IABTransportMigrationManagementRequest ::= SEQUENCE {
	protocolIEs			ProtocolIE-Container	{{ IABTransportMigrationManagementRequest-IEs}},
	...
}

IABTransportMigrationManagementRequest-IEs XNAP-PROTOCOL-IES ::= {
	{ ID id-F1-Terminating-IAB-DonorUEXnAPID		CRITICALITY reject		TYPE NG-RANnodeUEXnAPID						PRESENCE mandatory}|
	{ ID id-nonF1-Terminating-IAB-DonorUEXnAPID		CRITICALITY reject		TYPE NG-RANnodeUEXnAPID						PRESENCE mandatory}|
	{ ID id-TrafficToBeAddedList					CRITICALITY reject		TYPE TrafficToBeAddedList					PRESENCE optional }|
	{ ID id-TrafficToBeModifiedList					CRITICALITY reject		TYPE TrafficToBeModifiedList				PRESENCE optional }|
	{ ID id-TrafficToBeReleaseInformation			CRITICALITY reject		TYPE TrafficToBeReleaseInformation		PRESENCE optional }|
	{ ID id-IAB-TNL-Address-Request					CRITICALITY reject		TYPE IAB-TNL-Address-Request				PRESENCE optional }|
	{ ID id-IABTNLAddressException					CRITICALITY reject		TYPE IABTNLAddressException					PRESENCE optional },
	...
}

TrafficToBeAddedList ::= SEQUENCE (SIZE(1..maxnoofTrafficIndexEntries)) OF TrafficToBeAdded-Item

TrafficToBeAdded-Item ::= SEQUENCE {
	trafficIndex			TrafficIndex,
	trafficProfile			TrafficProfile,
	f1-TerminatingTopologyBHInformation		F1-TerminatingTopologyBHInformation		OPTIONAL,
	iE-Extensions			ProtocolExtensionContainer { {TrafficToBeAdded-Item-ExtIEs} }	OPTIONAL,
	...
}

TrafficToBeAdded-Item-ExtIEs XNAP-PROTOCOL-EXTENSION ::= {
	...
}

TrafficToBeModifiedList ::= SEQUENCE (SIZE(1..maxnoofTrafficIndexEntries)) OF TrafficToBeModified-Item

TrafficToBeModified-Item ::= SEQUENCE {
	trafficIndex			TrafficIndex,
	trafficProfile			TrafficProfile		OPTIONAL,
	f1-TerminatingTopologyBHInformation		F1-TerminatingTopologyBHInformation		OPTIONAL,
	iE-Extension			ProtocolExtensionContainer { {TrafficToBeModified-Item-ExtIEs} }	OPTIONAL,
	...
}

TrafficToBeModified-Item-ExtIEs XNAP-PROTOCOL-EXTENSION ::= {
	...
}

-- **************************************************************
--
-- IAB TRANSPORT MIGRATION MANAGEMENT RESPONSE
--
-- **************************************************************

IABTransportMigrationManagementResponse ::= SEQUENCE {
	protocolIEs			ProtocolIE-Container	{{ IABTransportMigrationManagementResponse-IEs}},
	...
}

IABTransportMigrationManagementResponse-IEs XNAP-PROTOCOL-IES ::= {
	{ ID id-F1-Terminating-IAB-DonorUEXnAPID		CRITICALITY reject		TYPE NG-RANnodeUEXnAPID						PRESENCE mandatory}|
	{ ID id-nonF1-Terminating-IAB-DonorUEXnAPID		CRITICALITY reject		TYPE NG-RANnodeUEXnAPID						PRESENCE mandatory}|
	{ ID id-TrafficAddedList						CRITICALITY reject		TYPE TrafficAddedList							PRESENCE optional }|
	{ ID id-TrafficModifiedList						CRITICALITY reject		TYPE TrafficModifiedList						PRESENCE optional }|
	{ ID id-TrafficNotAddedList						CRITICALITY reject		TYPE TrafficNotAddedList						PRESENCE optional }|
	{ ID id-TrafficNotModifiedList					CRITICALITY reject		TYPE TrafficNotModifiedList					PRESENCE optional }|
	{ ID id-IAB-TNL-Address-Response				CRITICALITY reject		TYPE IAB-TNL-Address-Response				PRESENCE optional }|
	{ ID id-TrafficReleasedList						CRITICALITY reject		TYPE TrafficReleasedList						PRESENCE optional },
	...
}

TrafficAddedList ::= SEQUENCE (SIZE(1..maxnoofTrafficIndexEntries)) OF TrafficAdded-Item

TrafficAdded-Item ::= SEQUENCE {
	trafficIndex			TrafficIndex,
	non-F1-TerminatingTopologyBHInformation		Non-F1-TerminatingTopologyBHInformation,
	iE-Extensions			ProtocolExtensionContainer { {TrafficAdded-Item-ExtIEs} }	OPTIONAL,
	...
}

TrafficAdded-Item-ExtIEs XNAP-PROTOCOL-EXTENSION ::= {
	...
}

TrafficModifiedList ::= SEQUENCE (SIZE(1..maxnoofTrafficIndexEntries)) OF TrafficModified-Item

TrafficModified-Item ::= SEQUENCE {
	trafficIndex			TrafficIndex,
	non-F1-TerminatingTopologyBHInformation		Non-F1-TerminatingTopologyBHInformation,
	iE-Extensions			ProtocolExtensionContainer { {TrafficModified-Item-ExtIEs} }	OPTIONAL,
	...
}

TrafficModified-Item-ExtIEs XNAP-PROTOCOL-EXTENSION ::= {
	...
}

TrafficNotAddedList ::= SEQUENCE (SIZE(1..maxnoofTrafficIndexEntries)) OF TrafficNotAdded-Item

TrafficNotAdded-Item ::= SEQUENCE {
	trafficIndex			TrafficIndex,
	casue					Cause			OPTIONAL,
	iE-Extensions			ProtocolExtensionContainer { {TrafficNotAdded-Item-ExtIEs} }	OPTIONAL,
	...
}

TrafficNotAdded-Item-ExtIEs XNAP-PROTOCOL-EXTENSION ::= {
	...
}

TrafficNotModifiedList ::= SEQUENCE (SIZE(1..maxnoofTrafficIndexEntries)) OF TrafficNotModified-Item

TrafficNotModified-Item ::= SEQUENCE {
	trafficIndex			TrafficIndex,
	cause					Cause		OPTIONAL,
	iE-Extensions			ProtocolExtensionContainer { {TrafficNotModified-Item-ExtIEs} }	OPTIONAL,
	...
}

TrafficNotModified-Item-ExtIEs XNAP-PROTOCOL-EXTENSION ::= {
	...
}


TrafficReleasedList ::= SEQUENCE (SIZE(1..maxnoofTrafficIndexEntries)) OF TrafficReleased-Item

TrafficReleased-Item ::= SEQUENCE {
	trafficIndex			TrafficIndex,
	bHInfoList				BHInfoList		OPTIONAL,
	iE-Extensions			ProtocolExtensionContainer { { TrafficReleased-Item-ExtIEs} }	OPTIONAL,
	...
}

TrafficReleased-Item-ExtIEs XNAP-PROTOCOL-EXTENSION ::= {
	...
}


-- **************************************************************
--
-- IAB TRANSPORT MIGRATION MANAGEMENT REJECT
--
-- **************************************************************

IABTransportMigrationManagementReject ::= SEQUENCE {
	protocolIEs			ProtocolIE-Container	{{ IABTransportMigrationManagementReject-IEs}},
	...
}

IABTransportMigrationManagementReject-IEs XNAP-PROTOCOL-IES ::= {
	{ ID id-F1-Terminating-IAB-DonorUEXnAPID		CRITICALITY reject		TYPE NG-RANnodeUEXnAPID						PRESENCE mandatory}|
	{ ID id-nonF1-Terminating-IAB-DonorUEXnAPID		CRITICALITY reject		TYPE NG-RANnodeUEXnAPID						PRESENCE mandatory}|
	{ ID id-Cause									CRITICALITY ignore		TYPE Cause										PRESENCE mandatory}|
	{ ID id-CriticalityDiagnostics					CRITICALITY ignore		TYPE CriticalityDiagnostics					PRESENCE optional },
	...
}


-- **************************************************************
--
-- IAB TRANSPORT MIGRATION MODIFICATION REQUEST
--
-- **************************************************************

IABTransportMigrationModificationRequest ::= SEQUENCE {
	protocolIEs			ProtocolIE-Container	{{ IABTransportMigrationModificationRequest-IEs}},
	...
}

IABTransportMigrationModificationRequest-IEs XNAP-PROTOCOL-IES ::= {
	{ ID id-F1-Terminating-IAB-DonorUEXnAPID			CRITICALITY reject	TYPE NG-RANnodeUEXnAPID							PRESENCE mandatory}|
	{ ID id-nonF1-Terminating-IAB-DonorUEXnAPID			CRITICALITY reject	TYPE NG-RANnodeUEXnAPID							PRESENCE mandatory}|
	{ ID id-TrafficRequiredToBeModifiedList				CRITICALITY reject	TYPE TrafficRequiredToBeModifiedList			PRESENCE optional }|
	{ ID id-TrafficToBeReleaseInformation				CRITICALITY reject	TYPE TrafficToBeReleaseInformation			PRESENCE optional }|
	{ ID id-IABTNLAddressToBeAdded						CRITICALITY reject	TYPE IAB-TNL-Address-Response					PRESENCE optional }|
	{ ID id-IABTNLAddressToBeReleasedList				CRITICALITY reject	TYPE IABTNLAddressToBeReleasedList			PRESENCE optional },
	...
}

TrafficRequiredToBeModifiedList ::= SEQUENCE (SIZE(1..maxnoofTrafficIndexEntries)) OF TrafficRequiredToBeModified-Item

TrafficRequiredToBeModified-Item ::= SEQUENCE {
	trafficIndex			TrafficIndex,
	non-f1-TerminatingTopologyBHInformation		Non-F1-TerminatingTopologyBHInformation,
	iE-Extensions			ProtocolExtensionContainer{ { TrafficRequiredToBeModified-Item-ExtIEs} }		OPTIONAL,
	...
}

TrafficRequiredToBeModified-Item-ExtIEs XNAP-PROTOCOL-EXTENSION ::= {
	...
}

IABTNLAddressToBeReleasedList ::= SEQUENCE (SIZE(1..maxnoofTLAsIAB)) OF IABTNLAddressToBeReleased-Item

IABTNLAddressToBeReleased-Item ::= SEQUENCE {
	iabTNLAddress			IABTNLAddress,
	iE-Extensions			ProtocolExtensionContainer{ { IABTNLAddressToBeReleased-Item-ExtIEs} }	OPTIONAL,
	...
}

IABTNLAddressToBeReleased-Item-ExtIEs XNAP-PROTOCOL-EXTENSION ::= {
	...
}



-- **************************************************************
--
-- IAB TRANSPORT MIGRATION MODIFICATION RESPONSE
--
-- **************************************************************

IABTransportMigrationModificationResponse ::= SEQUENCE {
	protocolIEs			ProtocolIE-Container	{{ IABTransportMigrationModificationResponse-IEs}},
	...
}

IABTransportMigrationModificationResponse-IEs XNAP-PROTOCOL-IES ::= {
	{ ID id-F1-Terminating-IAB-DonorUEXnAPID			CRITICALITY reject	TYPE NG-RANnodeUEXnAPID						PRESENCE mandatory}|
	{ ID id-nonF1-Terminating-IAB-DonorUEXnAPID			CRITICALITY reject	TYPE NG-RANnodeUEXnAPID						PRESENCE mandatory}|
	{ ID id-TrafficRequiredModifiedList					CRITICALITY reject	TYPE TrafficRequiredModifiedList			PRESENCE optional }|
	{ ID id-TrafficReleasedList							CRITICALITY reject	TYPE TrafficReleasedList						PRESENCE optional },
	...
}



TrafficRequiredModifiedList ::= SEQUENCE (SIZE(1..maxnoofTrafficIndexEntries)) OF TrafficRequiredModified-Item

TrafficRequiredModified-Item ::= SEQUENCE {
	trafficIndex			TrafficIndex,
	iE-Extensions			ProtocolExtensionContainer { { TrafficRequiredModified-Item-ExtIEs} }	OPTIONAL,
	...
}

TrafficRequiredModified-Item-ExtIEs XNAP-PROTOCOL-EXTENSION ::= {
	...
}


-- **************************************************************
--
-- IAB RESOURCE COORDINATION REQUEST
--
-- **************************************************************

IABResourceCoordinationRequest ::= SEQUENCE {
	protocolIEs			ProtocolIE-Container	{{ IABResourceCoordinationRequest-IEs}},
	...
}

IABResourceCoordinationRequest-IEs XNAP-PROTOCOL-IES ::= {
	{ ID id-F1-Terminating-IAB-DonorUEXnAPID	CRITICALITY reject		TYPE NG-RANnodeUEXnAPID					PRESENCE mandatory}|
	{ ID id-nonF1-Terminating-IAB-DonorUEXnAPID	CRITICALITY reject		TYPE NG-RANnodeUEXnAPID					PRESENCE mandatory}|
	{ ID id-BoundaryNodeCellsList				CRITICALITY reject		TYPE BoundaryNodeCellsList			PRESENCE optional }|
	{ ID id-ParentNodeCellsList					CRITICALITY reject		TYPE ParentNodeCellsList				PRESENCE optional },
	...
}


BoundaryNodeCellsList ::= SEQUENCE (SIZE(1..maxnoofServedCellsIAB)) OF BoundaryNodeCellsList-Item

BoundaryNodeCellsList-Item ::= SEQUENCE {
	boundaryNodeCellInformation			IABCellInformation,
	iE-Extensions						ProtocolExtensionContainer { {BoundaryNodeCellsList-Item-ExtIEs} }		OPTIONAL,
	...
}

BoundaryNodeCellsList-Item-ExtIEs XNAP-PROTOCOL-EXTENSION ::= {
	...
}

ParentNodeCellsList ::= SEQUENCE (SIZE(1..maxnoofServingCells)) OF ParentNodeCellsList-Item

ParentNodeCellsList-Item ::= SEQUENCE {
	parentNodeCellInformation			IABCellInformation,
	iE-Extensions						ProtocolExtensionContainer { {ParentNodeCellsList-Item-ExtIEs} }	OPTIONAL,
	...
}

ParentNodeCellsList-Item-ExtIEs XNAP-PROTOCOL-EXTENSION ::= {
	...
}


-- **************************************************************
--
-- IAB RESOURCE COORDINATION RESPONSE
--
-- **************************************************************

IABResourceCoordinationResponse ::= SEQUENCE {
	protocolIEs			ProtocolIE-Container	{{ IABResourceCoordinationResponse-IEs}},
	...
}

IABResourceCoordinationResponse-IEs XNAP-PROTOCOL-IES ::= {
	{ ID id-F1-Terminating-IAB-DonorUEXnAPID		CRITICALITY reject		TYPE NG-RANnodeUEXnAPID					PRESENCE mandatory}|
	{ ID id-nonF1-Terminating-IAB-DonorUEXnAPID		CRITICALITY reject		TYPE NG-RANnodeUEXnAPID					PRESENCE mandatory}|
	{ ID id-BoundaryNodeCellsList					CRITICALITY reject		TYPE BoundaryNodeCellsList				PRESENCE optional }|
	{ ID id-ParentNodeCellsList						CRITICALITY reject		TYPE ParentNodeCellsList					PRESENCE optional },
	...
}

-- **************************************************************
--
-- CONDITIONAL PSCELL CHANGE CANCEL
--
-- **************************************************************

CPCCancel ::= SEQUENCE {
	protocolIEs			ProtocolIE-Container	{{ CPCCancel-IEs}},
	...
}
CPCCancel-IEs XNAP-PROTOCOL-IES ::= {
	{ ID id-M-NG-RANnodeUEXnAPID				CRITICALITY reject		TYPE NG-RANnodeUEXnAPID							PRESENCE mandatory}|
	{ ID id-S-NG-RANnodeUEXnAPID				CRITICALITY reject		TYPE NG-RANnodeUEXnAPID							PRESENCE mandatory}|
	{ ID id-Cause								CRITICALITY ignore		TYPE Cause										PRESENCE optional }|
	{ ID id-target-S-NG-RANnodeID				CRITICALITY reject		TYPE GlobalNG-RANNode-ID						PRESENCE mandatory},
	...
}

-- **************************************************************
--
-- PARTIAL UE CONTEXT TRANSFER
--
-- **************************************************************
PartialUEContextTransfer ::= SEQUENCE {
	protocolIEs			ProtocolIE-Container	{{ PartialUEContextTransfer-IEs}},
	...
}

PartialUEContextTransfer-IEs XNAP-PROTOCOL-IES ::= {
	{ ID id-newNG-RANnodeUEXnAPID					CRITICALITY reject		TYPE NG-RANnodeUEXnAPID							PRESENCE mandatory}|
	{ ID id-oldNG-RANnodeUEXnAPID					CRITICALITY ignore		TYPE NG-RANnodeUEXnAPID							PRESENCE mandatory}|
	{ ID id-SDTPartialUEContextInfo					CRITICALITY ignore		TYPE SDTPartialUEContextInfo					PRESENCE mandatory},
	...
}

-- **************************************************************
--
-- PARTIAL UE CONTEXT TRANSFER ACKNOWLEDGE
--
-- **************************************************************
PartialUEContextTransferAcknowledge ::= SEQUENCE {
	protocolIEs			ProtocolIE-Container	{{ PartialUEContextTransferAcknowledge-IEs}},
	...
}

PartialUEContextTransferAcknowledge-IEs XNAP-PROTOCOL-IES ::= {
	{ ID id-newNG-RANnodeUEXnAPID					CRITICALITY ignore		TYPE NG-RANnodeUEXnAPID							PRESENCE mandatory}|
	{ ID id-oldNG-RANnodeUEXnAPID					CRITICALITY ignore		TYPE NG-RANnodeUEXnAPID							PRESENCE mandatory}|
	{ ID id-SDTDataForwardingDRBList				CRITICALITY ignore		TYPE SDTDataForwardingDRBList					PRESENCE optional }|
	{ ID id-CriticalityDiagnostics					CRITICALITY ignore		TYPE CriticalityDiagnostics						PRESENCE optional },
	...
}

-- **************************************************************
--
-- PARTIAL UE CONTEXT TRANSFER FAILURE
--
-- **************************************************************

PartialUEContextTransferFailure::= SEQUENCE {
	protocolIEs			ProtocolIE-Container	{{ PartialUEContextTransferFailure-IEs}},
	...
}

PartialUEContextTransferFailure-IEs XNAP-PROTOCOL-IES ::= {
	{ ID id-newNG-RANnodeUEXnAPID					CRITICALITY ignore		TYPE NG-RANnodeUEXnAPID							PRESENCE mandatory}|
	{ ID id-oldNG-RANnodeUEXnAPID					CRITICALITY ignore		TYPE NG-RANnodeUEXnAPID							PRESENCE mandatory}|
	{ ID id-Cause									CRITICALITY ignore		TYPE Cause											PRESENCE mandatory}|
	{ ID id-CriticalityDiagnostics					CRITICALITY ignore		TYPE CriticalityDiagnostics						PRESENCE optional },
	...
}


END

RFC1157-SNMP DEFINITIONS ::= BEGIN

    IMPORTS
          ObjectName, ObjectSyntax, NetworkAddress, IpAddress, TimeTicks
          FROM RFC1155-SMI;

          -- top-level message

          Message ::= SEQUENCE {
                      version INTEGER {             -- version-1 for this RFC
                              version-1(0)
                          },
                      community OCTET STRING,       -- community name
                      data ANY                      -- e.g., PDUs if trivial
                                                    -- authentication is being used
                  }

          -- protocol data units

          PDUs ::= CHOICE {
                     get-request GetRequest-PDU,
                     get-next-request GetNextRequest-PDU,
                     get-response GetResponse-PDU,
                     set-request SetRequest-PDU,
                     trap Trap-PDU
                  }

          -- PDUs

          GetRequest-PDU ::= [0] IMPLICIT PDU

          GetNextRequest-PDU ::= [1] IMPLICIT PDU

          GetResponse-PDU ::= [2] IMPLICIT PDU

          SetRequest-PDU ::= [3] IMPLICIT PDU

          PDU ::= SEQUENCE {
                     request-id INTEGER,
                     error-status INTEGER {         -- sometimes ignored
                              noError(0),
                              tooBig(1),
                              noSuchName(2),
                              badValue(3),
                              readOnly(4),
                              genErr(5)
                          },
                     error-index INTEGER,           -- sometimes ignored
                     variable-bindings VarBindList  -- values are sometimes ignored
                  }

          Trap-PDU ::= [4] IMPLICIT SEQUENCE {
                     enterprise OBJECT IDENTIFIER,  -- type of object generating
                                                    -- trap, see sysObjectID in [5]
                     agent-addr NetworkAddress,     -- address of object generating
                                                    -- trap
                     generic-trap INTEGER {         -- generic trap type
                             coldStart(0),
                             warmStart(1),
                             linkDown(2),
                             linkUp(3),
                             authenticationFailure(4),
                             egpNeighborLoss(5),
                             enterpriseSpecific(6)
                         },                        
                     specific-trap INTEGER,         -- specific code, present even
                                                    -- if generic-trap is not
                                                    -- enterpriseSpecific
                     time-stamp TimeTicks,          -- time elapsed between the last
                                                    -- (re)initialization of the network
                                                    -- entity and the generation of the trap
                     variable-bindings VarBindList  -- "interesting" information  
                  }

          -- variable bindings

          VarBind ::= SEQUENCE {
                      name ObjectName,
                      value ObjectSyntax
                  }

         VarBindList ::= SEQUENCE OF VarBind

    END

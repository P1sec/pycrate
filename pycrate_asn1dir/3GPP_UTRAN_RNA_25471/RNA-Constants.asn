-- **************************************************************
--
-- Constant definitions
--
-- **************************************************************

RNA-Constants {
itu-t (0) identified-organization (4) etsi (0) mobileDomain (0)
umts-Access (20) modules (3) rna(7) version1 (1) rna-Constants (4) }

DEFINITIONS AUTOMATIC TAGS ::=

BEGIN

IMPORTS
	ProcedureCode,
	ProtocolIE-ID
FROM RNA-CommonDataTypes;


-- **************************************************************
--
-- Elementary Procedures
--
-- **************************************************************
id-IurhSetup						ProcedureCode ::= 1
id-Connect							ProcedureCode ::= 2
id-DirectTransfer					ProcedureCode ::= 3
id-Disconnect						ProcedureCode ::= 4
id-ConnectionlessTransfer			ProcedureCode ::= 5
id-ErrorIndication					ProcedureCode ::= 6
id-privateMessage					ProcedureCode ::= 7


-- **************************************************************
--
-- Lists
--
-- **************************************************************
maxNrOfErrors						INTEGER ::= 256



-- **************************************************************
--
-- IEs
--
-- **************************************************************

id-Cause										ProtocolIE-ID ::= 1
id-CriticalityDiagnostics						ProtocolIE-ID ::= 2
id-RNSAP-Message								ProtocolIE-ID ::= 3
id-BackoffTimer									ProtocolIE-ID ::= 4
id-Senders-HNB-RNL-ID							ProtocolIE-ID ::= 5
id-Receivers-HNB-RNL-ID							ProtocolIE-ID ::= 6
id-Iurh-Signalling-Context-ID					ProtocolIE-ID ::= 7
id-HNB-RNL-ID									ProtocolIE-ID ::= 8
id-HNB-Cell-Identifier							ProtocolIE-ID ::= 9
id-GlobalRNC-ID									ProtocolIE-ID ::= 10




END

GPRSChargingDataTypes {itu-t (0) identified-organization (4) etsi (0) mobileDomain (0) charging (5) gprsChargingDataTypes (2) asn1Module (0) version2 (1)}
DEFINITIONS IMPLICIT TAGS	::=

BEGIN

-- EXPORTS everything

IMPORTS

AddressString,
CallDuration,
CallingNumber,
CauseForRecClosing,
CellId,
ChargingID,
CivicAddressInformation,
Diagnostics,
DiameterIdentity,
DynamicAddressFlag,
EnhancedDiagnostics,
GSNAddress,
InvolvedParty,
IPAddress,
LCSCause,
LCSClientIdentity,
LCSQoSInfo,
LevelOfCAMELService,
LocalSequenceNumber,
LocationAreaAndCell,
LocationAreaCode,
ManagementExtensions,
MBMSInformation,
MessageReference,
MSISDN,
MSTimeZone,
NodeID,
PDPAddress,
PLMN-Id,
PositioningData,
RATType,
RecordingEntity,
RecordType,
RoutingAreaCode,
SCSASAddress,
ServiceSpecificInfo,
SMSResult,
SmsTpDestinationNumber,
SubscriptionID,
ThreeGPPPSDataOffStatus,
TimeStamp
FROM GenericChargingDataTypes {itu-t (0) identified-organization (4) etsi(0) mobileDomain (0) charging (5) genericChargingDataTypes (0) asn1Module (0) version2 (1)}

DefaultGPRS-Handling,
DefaultSMS-Handling,
NotificationToMSUser,
ServiceKey
FROM MAP-MS-DataTypes {itu-t identified-organization (4) etsi (0) mobileDomain (0)
gsm-Network (1) modules (3) map-MS-DataTypes (11) version18 (18)}
-- from TS 29.002 [214]

IMEI,
IMSI,
ISDN-AddressString,
RAIdentity
FROM MAP-CommonDataTypes {itu-t identified-organization (4) etsi (0) mobileDomain (0)gsm-Network (1) modules (3) map-CommonDataTypes (18) version18 (18)}
-- from TS 29.002 [214]

CallReferenceNumber
FROM MAP-CH-DataTypes {itu-t identified-organization (4) etsi (0) mobileDomain (0)gsm-Network (1) modules (3) map-CH-DataTypes (13) version18 (18)}
-- from TS 29.002 [214]

Ext-GeographicalInformation,
LCSClientType,
LCS-Priority,
LocationType
FROM MAP-LCS-DataTypes {itu-t identified-organization (4) etsi (0) mobileDomain (0) gsm-Network (1) modules (3) map-LCS-DataTypes (25) version18 (18) }
-- from TS 29.002 [214]

LocationMethod
FROM SS-DataTypes {itu-t identified-organization (4) etsi (0) mobileDomain (0) gsm-Access (2) modules (3) ss-DataTypes (2) version14 (14)}
-- from TS 24.080 [209]

;

--
--  GPRS RECORDS
--

GPRSRecord	::= CHOICE
--
-- Record values 20, 22..27 are specific
-- Record values 76, 77, 86 are MBMS specific
-- Record values 78,79 and 92, 95, 96 are EPC specific
--
{
	sgsnPDPRecord			[20] SGSNPDPRecord,
	sgsnMMRecord			[22] SGSNMMRecord,
	sgsnSMORecord			[23] SGSNSMORecord,
	sgsnSMTRecord			[24] SGSNSMTRecord,
	sgsnMTLCSRecord			[25] SGSNMTLCSRecord,
	sgsnMOLCSRecord			[26] SGSNMOLCSRecord,
	sgsnNILCSRecord			[27] SGSNNILCSRecord,

	sgsnMBMSRecord			[76] SGSNMBMSRecord,
	ggsnMBMSRecord			[77] GGSNMBMSRecord,
	sGWRecord				[78] SGWRecord,
	pGWRecord				[79] PGWRecord,

	gwMBMSRecord			[86] GWMBMSRecord,

	tDFRecord				[92] TDFRecord,

	iPERecord				[95] IPERecord,
	ePDGRecord				[96] EPDGRecord,
	tWAGRecord				[97] TWAGRecord
}

SGWRecord 	::= SET
{
	recordType					[0] RecordType,
	servedIMSI					[3] IMSI OPTIONAL,
	s-GWAddress					[4] GSNAddress,
	chargingID					[5] ChargingID,
	servingNodeAddress			[6] SEQUENCE OF GSNAddress,
	accessPointNameNI			[7] AccessPointNameNI OPTIONAL,
	pdpPDNType					[8] PDPType OPTIONAL,
	servedPDPPDNAddress			[9] PDPAddress OPTIONAL,
	dynamicAddressFlag			[11] DynamicAddressFlag OPTIONAL,
	listOfTrafficVolumes		[12] SEQUENCE OF ChangeOfCharCondition OPTIONAL,
	recordOpeningTime			[13] TimeStamp,
	duration					[14] CallDuration,
	causeForRecClosing			[15] CauseForRecClosing,
	diagnostics					[16] Diagnostics OPTIONAL,
	recordSequenceNumber		[17] INTEGER OPTIONAL,
	nodeID						[18] NodeID OPTIONAL,
	recordExtensions			[19] ManagementExtensions OPTIONAL,
	localSequenceNumber			[20] LocalSequenceNumber OPTIONAL,
	apnSelectionMode			[21] APNSelectionMode OPTIONAL,
	servedMSISDN				[22] MSISDN OPTIONAL,
	chargingCharacteristics		[23] ChargingCharacteristics,
	chChSelectionMode			[24] ChChSelectionMode OPTIONAL,
	iMSsignalingContext			[25] NULL OPTIONAL,
	servingNodePLMNIdentifier	[27] PLMN-Id OPTIONAL,
	servedIMEI					[29] IMEI OPTIONAL,
	rATType						[30] RATType OPTIONAL,
	mSTimeZone 					[31] MSTimeZone OPTIONAL,
	userLocationInformation		[32] OCTET STRING OPTIONAL,
	sGWChange					[34] SGWChange OPTIONAL,
	servingNodeType				[35] SEQUENCE OF ServingNodeType,
	p-GWAddressUsed				[36] GSNAddress OPTIONAL,
	p-GWPLMNIdentifier			[37] PLMN-Id OPTIONAL,
	startTime					[38] TimeStamp OPTIONAL,
	stopTime					[39] TimeStamp OPTIONAL,
	pDNConnectionChargingID		[40] ChargingID OPTIONAL,
	iMSIunauthenticatedFlag 	[41] NULL OPTIONAL,
	userCSGInformation			[42] UserCSGInformation OPTIONAL,
	servedPDPPDNAddressExt 		[43] PDPAddress OPTIONAL,
	lowPriorityIndicator		[44] NULL OPTIONAL,
	dynamicAddressFlagExt		[47] DynamicAddressFlag OPTIONAL,
	s-GWiPv6Address				[48] GSNAddress OPTIONAL,
	servingNodeiPv6Address		[49] SEQUENCE OF GSNAddress OPTIONAL,
	p-GWiPv6AddressUsed			[50] GSNAddress OPTIONAL,
	retransmission				[51] NULL OPTIONAL,
	userLocationInfoTime		[52] TimeStamp OPTIONAL,
	cNOperatorSelectionEnt		[53] CNOperatorSelectionEntity OPTIONAL,
	presenceReportingAreaInfo	[54] PresenceReportingAreaInfo OPTIONAL,
	lastUserLocationInformation	[55] OCTET STRING OPTIONAL,
	lastMSTimeZone				[56] MSTimeZone OPTIONAL,
	enhancedDiagnostics			[57] EnhancedDiagnostics OPTIONAL,
	cPCIoTEPSOptimisationIndicator [59] CPCIoTEPSOptimisationIndicator OPTIONAL,
	uNIPDUCPOnlyFlag			[60] UNIPDUCPOnlyFlag OPTIONAL,
	servingPLMNRateControl		[61] ServingPLMNRateControl OPTIONAL,
	pDPPDNTypeExtension			[62] PDPPDNTypeExtension OPTIONAL,
	mOExceptionDataCounter		[63] MOExceptionDataCounter OPTIONAL,
	listOfRANSecondaryRATUsageReports [64] SEQUENCE OF RANSecondaryRATUsageReport OPTIONAL
}

PGWRecord 	::= SET
--
--	List of traffic volumes is only applicable when Charging per IP-CAN session is active and
--	IP-CAN bearer charging is being performed for the session.
--
--	EPC QoS Information is only applicable when Charging per IP-CAN session is active.
--
{
	recordType						[0] RecordType,
	servedIMSI						[3] IMSI OPTIONAL,
	p-GWAddress						[4] GSNAddress,
	chargingID						[5] ChargingID,
	servingNodeAddress				[6] SEQUENCE OF GSNAddress,
	accessPointNameNI				[7] AccessPointNameNI OPTIONAL,
	pdpPDNType						[8] PDPType OPTIONAL,
	servedPDPPDNAddress				[9] PDPAddress OPTIONAL,
	dynamicAddressFlag				[11] DynamicAddressFlag OPTIONAL,
	listOfTrafficVolumes			[12] SEQUENCE OF ChangeOfCharCondition OPTIONAL,
	recordOpeningTime				[13] TimeStamp,
	duration						[14] CallDuration,
	causeForRecClosing				[15] CauseForRecClosing,
	diagnostics						[16] Diagnostics OPTIONAL,
	recordSequenceNumber			[17] INTEGER OPTIONAL,
	nodeID							[18] NodeID OPTIONAL,
	recordExtensions				[19] ManagementExtensions OPTIONAL,
	localSequenceNumber				[20] LocalSequenceNumber OPTIONAL,
	apnSelectionMode				[21] APNSelectionMode OPTIONAL,
	servedMSISDN					[22] MSISDN OPTIONAL,
	chargingCharacteristics			[23] ChargingCharacteristics,
	chChSelectionMode				[24] ChChSelectionMode OPTIONAL,
	iMSsignalingContext				[25] NULL OPTIONAL,
	servingNodePLMNIdentifier		[27] PLMN-Id OPTIONAL,
	pSFurnishChargingInformation	[28] PSFurnishChargingInformation OPTIONAL,
	servedIMEI						[29] IMEI OPTIONAL,
	rATType							[30] RATType OPTIONAL,
	mSTimeZone 						[31] MSTimeZone OPTIONAL,
	userLocationInformation			[32] OCTET STRING OPTIONAL,
	cAMELChargingInformation		[33] OCTET STRING OPTIONAL,
	listOfServiceData				[34] SEQUENCE OF ChangeOfServiceCondition OPTIONAL,
	servingNodeType					[35] SEQUENCE OF ServingNodeType,
	servedMNNAI						[36] SubscriptionID OPTIONAL,
	p-GWPLMNIdentifier				[37] PLMN-Id OPTIONAL,
	startTime						[38] TimeStamp OPTIONAL,
	stopTime						[39] TimeStamp OPTIONAL,
	served3gpp2MEID					[40] OCTET STRING OPTIONAL,
	pDNConnectionChargingID			[41] ChargingID OPTIONAL,
	iMSIunauthenticatedFlag 		[42] NULL OPTIONAL,
	userCSGInformation				[43] UserCSGInformation OPTIONAL,
	threeGPP2UserLocationInformation	[44] OCTET STRING OPTIONAL,
	servedPDPPDNAddressExt 				[45] PDPAddress OPTIONAL,
	lowPriorityIndicator				[46] NULL OPTIONAL,
	dynamicAddressFlagExt				[47] DynamicAddressFlag OPTIONAL,
	servingNodeiPv6Address				[49] SEQUENCE OF GSNAddress OPTIONAL,
	p-GWiPv6AddressUsed					[50] GSNAddress OPTIONAL,
	tWANUserLocationInformation			[51] TWANUserLocationInfo OPTIONAL,
	retransmission   					[52] NULL OPTIONAL,
	userLocationInfoTime				[53] TimeStamp OPTIONAL,
	cNOperatorSelectionEnt		    	[54] CNOperatorSelectionEntity OPTIONAL,
	ePCQoSInformation					[55] EPCQoSInformation OPTIONAL,
	presenceReportingAreaInfo			[56] PresenceReportingAreaInfo OPTIONAL,
	lastUserLocationInformation			[57] OCTET STRING OPTIONAL,
	lastMSTimeZone						[58] MSTimeZone OPTIONAL,
	enhancedDiagnostics					[59] EnhancedDiagnostics OPTIONAL,
	nBIFOMMode							[60] NBIFOMMode OPTIONAL,
	nBIFOMSupport						[61] NBIFOMSupport OPTIONAL,
	uWANUserLocationInformation			[62] UWANUserLocationInfo OPTIONAL,
	sGiPtPTunnellingMethod				[64] SGiPtPTunnellingMethod OPTIONAL,
	uNIPDUCPOnlyFlag					[65] UNIPDUCPOnlyFlag OPTIONAL,
	servingPLMNRateControl				[66] ServingPLMNRateControl OPTIONAL,
	aPNRateControl						[67] APNRateControl OPTIONAL,
	pDPPDNTypeExtension					[68] PDPPDNTypeExtension OPTIONAL,
	mOExceptionDataCounter				[69] MOExceptionDataCounter OPTIONAL,
	chargingPerIPCANSessionIndicator    [70] ChargingPerIPCANSessionIndicator OPTIONAL,
	threeGPPPSDataOffStatus				[71] ThreeGPPPSDataOffStatus OPTIONAL,
	sCSASAddress						[72] SCSASAddress OPTIONAL,
	listOfRANSecondaryRATUsageReports	[73] SEQUENCE OF RANSecondaryRATUsageReport OPTIONAL
}

TDFRecord 	::= SET
{
	recordType						[0] RecordType,
	servedIMSI						[3] IMSI OPTIONAL,
	p-GWAddress						[4] GSNAddress,
	servingNodeAddress				[6] SEQUENCE OF GSNAddress,
	accessPointNameNI				[7] AccessPointNameNI OPTIONAL,
	pdpPDNType						[8] PDPType OPTIONAL,
	servedPDPPDNAddress				[9] PDPAddress OPTIONAL,
	dynamicAddressFlag				[11] DynamicAddressFlag OPTIONAL,
	recordOpeningTime				[13] TimeStamp,
	duration						[14] CallDuration,
	causeForRecClosing				[15] CauseForRecClosing,
	diagnostics						[16] Diagnostics OPTIONAL,
	recordSequenceNumber			[17] INTEGER OPTIONAL,
	nodeID							[18] NodeID OPTIONAL,
	recordExtensions				[19] ManagementExtensions OPTIONAL,
	localSequenceNumber				[20] LocalSequenceNumber OPTIONAL,
	apnSelectionMode				[21] APNSelectionMode OPTIONAL,
	servedMSISDN					[22] MSISDN OPTIONAL,
	chargingCharacteristics			[23] ChargingCharacteristics,
	chChSelectionMode				[24] ChChSelectionMode OPTIONAL,
	servingNodePLMNIdentifier		[27] PLMN-Id OPTIONAL,
	pSFurnishChargingInformation	[28] PSFurnishChargingInformation OPTIONAL,
	servedIMEI						[29] IMEI OPTIONAL,
	rATType							[30] RATType OPTIONAL,
	mSTimeZone 						[31] MSTimeZone OPTIONAL,
	userLocationInformation			[32] OCTET STRING OPTIONAL,
	listOfServiceData				[34] SEQUENCE OF ChangeOfServiceCondition OPTIONAL,
	servingNodeType					[35] SEQUENCE OF ServingNodeType,
	servedMNNAI						[36] SubscriptionID OPTIONAL,
	p-GWPLMNIdentifier				[37] PLMN-Id OPTIONAL,
	startTime						[38] TimeStamp OPTIONAL,
	stopTime						[39] TimeStamp OPTIONAL,
	served3gpp2MEID					[40] OCTET STRING OPTIONAL,
	pDNConnectionChargingID			[41] ChargingID,
	userCSGInformation				[43] UserCSGInformation OPTIONAL,
	threeGPP2UserLocationInformation	[44] OCTET STRING OPTIONAL,
	servedPDPPDNAddressExt 				[45] PDPAddress OPTIONAL,
	dynamicAddressFlagExt				[47] DynamicAddressFlag OPTIONAL,
	servingNodeiPv6Address				[49] SEQUENCE OF GSNAddress OPTIONAL,
	p-GWiPv6AddressUsed					[50] GSNAddress OPTIONAL,
	tWANUserLocationInformation			[51] TWANUserLocationInfo OPTIONAL,
	retransmission   					[52] NULL OPTIONAL,
	tDFAddress							[53] GSNAddress,
	tDFiPv6AddressUsed					[54] GSNAddress OPTIONAL,
	tDFPLMNIdentifier					[55] PLMN-Id OPTIONAL,
	servedFixedSubsID					[56] FixedSubsID OPTIONAL,
	accessLineIdentifier				[57] AccessLineIdentifier OPTIONAL,
	fixedUserLocationInformation		[59] FixedUserLocationInformation OPTIONAL
}

IPERecord 	::= SET
{
	recordType						[0] RecordType,
	servedIMSI						[3] IMSI OPTIONAL,
	iPEdgeAddress					[4] GSNAddress,
	chargingID						[5] ChargingID,
	accessPointNameNI				[7] AccessPointNameNI OPTIONAL,
	iPCANsessionType				[8] PDPType OPTIONAL,
	servedIPCANsessionAddress		[9] PDPAddress OPTIONAL,
	dynamicAddressFlag				[11] DynamicAddressFlag OPTIONAL,
	listOfTrafficVolumes			[12] SEQUENCE OF ChangeOfCharCondition OPTIONAL,
	recordOpeningTime				[13] TimeStamp,
	duration						[14] CallDuration,
	causeForRecClosing				[15] CauseForRecClosing,
	diagnostics						[16] Diagnostics OPTIONAL,
	recordSequenceNumber			[17] INTEGER OPTIONAL,
	nodeID							[18] NodeID OPTIONAL,
	recordExtensions				[19] ManagementExtensions OPTIONAL,
	localSequenceNumber				[20] LocalSequenceNumber OPTIONAL,
	servedMSISDN					[22] MSISDN OPTIONAL,
	chargingCharacteristics			[23] ChargingCharacteristics,
	chChSelectionMode				[24] ChChSelectionMode OPTIONAL,
	pSFurnishChargingInformation	[28] PSFurnishChargingInformation OPTIONAL,
	servedIMEI		   				[29] IMEI OPTIONAL,
	listOfServiceData				[34] SEQUENCE OF ChangeOfServiceCondition OPTIONAL,
	servedMNNAI						[36] SubscriptionID OPTIONAL,
	iPEdgeOperatorIdentifier		[37] PLMN-Id OPTIONAL,
	startTime						[38] TimeStamp OPTIONAL,
	stopTime						[39] TimeStamp OPTIONAL,
	servedIPCANsessionAddressExt 	[45] PDPAddress OPTIONAL,
	dynamicAddressFlagExt			[47] DynamicAddressFlag OPTIONAL,
	iPEdgeiPv6AddressUsed			[50] GSNAddress OPTIONAL,
	retransmission   				[52] NULL OPTIONAL,
	servedFixedSubsID				[55] FixedSubsID OPTIONAL,
	accessLineIdentifier			[56] AccessLineIdentifier OPTIONAL,
	fixedUserLocationInformation	[57] FixedUserLocationInformation OPTIONAL
}

EPDGRecord 	::= SET
{
	recordType					[0] RecordType,
	servedIMSI					[3] IMSI OPTIONAL,
	ePDGAddressUsed				[4] GSNAddress,
	chargingID					[5] ChargingID,
	accessPointNameNI			[7] AccessPointNameNI OPTIONAL,
	pdpPDNType					[8] PDPType OPTIONAL,
	servedPDPPDNAddress			[9] PDPAddress OPTIONAL,
	dynamicAddressFlag			[11] DynamicAddressFlag OPTIONAL,
	listOfTrafficVolumes		[12] SEQUENCE OF ChangeOfCharCondition OPTIONAL,
	recordOpeningTime			[13] TimeStamp,
	duration					[14] CallDuration,
	causeForRecClosing			[15] CauseForRecClosing,
	diagnostics					[16] Diagnostics OPTIONAL,
	recordSequenceNumber		[17] INTEGER OPTIONAL,
	nodeID						[18] NodeID OPTIONAL,
	recordExtensions			[19] ManagementExtensions OPTIONAL,
	localSequenceNumber			[20] LocalSequenceNumber OPTIONAL,
	apnSelectionMode			[21] APNSelectionMode OPTIONAL,
	servedMSISDN				[22] MSISDN OPTIONAL,
	chargingCharacteristics		[23] ChargingCharacteristics,
	chChSelectionMode			[24] ChChSelectionMode OPTIONAL,
	iMSsignalingContext			[25] NULL OPTIONAL,
	servedIMEI					[29] IMEI OPTIONAL,
	rATType						[30] RATType OPTIONAL,
	sGWChange					[34] SGWChange OPTIONAL,
	p-GWAddressUsed				[36] GSNAddress OPTIONAL,
	p-GWPLMNIdentifier			[37] PLMN-Id OPTIONAL,
	startTime					[38] TimeStamp OPTIONAL,
	stopTime					[39] TimeStamp OPTIONAL,
	pDNConnectionChargingID		[40] ChargingID OPTIONAL,
	servedPDPPDNAddressExt 		[43] PDPAddress OPTIONAL,
	dynamicAddressFlagExt		[47] DynamicAddressFlag OPTIONAL,
	ePDGiPv6AddressUsed			[48] GSNAddress OPTIONAL,
	p-GWiPv6AddressUsed			[50] GSNAddress OPTIONAL,
	retransmission				[51] NULL OPTIONAL,
	enhancedDiagnostics			[52] EnhancedDiagnostics OPTIONAL,
	uWANUserLocationInformation	[53] UWANUserLocationInfo OPTIONAL,
	userLocationInfoTime		[54] TimeStamp OPTIONAL,
	iMSIunauthenticatedFlag 	[55] NULL OPTIONAL
}

TWAGRecord 	::= SET
{
	recordType					[0] RecordType,
	servedIMSI					[3] IMSI OPTIONAL,
	tWAGAddressUsed				[4] GSNAddress,
	chargingID					[5] ChargingID,
	accessPointNameNI			[7] AccessPointNameNI OPTIONAL,
	pdpPDNType					[8] PDPType OPTIONAL,
	servedPDPPDNAddress			[9] PDPAddress OPTIONAL,
	dynamicAddressFlag			[11] DynamicAddressFlag OPTIONAL,
	listOfTrafficVolumes		[12] SEQUENCE OF ChangeOfCharCondition OPTIONAL,
	recordOpeningTime			[13] TimeStamp,
	duration					[14] CallDuration,
	causeForRecClosing			[15] CauseForRecClosing,
	diagnostics					[16] Diagnostics OPTIONAL,
	recordSequenceNumber		[17] INTEGER OPTIONAL,
	nodeID						[18] NodeID OPTIONAL,
	recordExtensions			[19] ManagementExtensions OPTIONAL,
	localSequenceNumber			[20] LocalSequenceNumber OPTIONAL,
	apnSelectionMode			[21] APNSelectionMode OPTIONAL,
	servedMSISDN				[22] MSISDN OPTIONAL,
	chargingCharacteristics		[23] ChargingCharacteristics,
	chChSelectionMode			[24] ChChSelectionMode OPTIONAL,
	servedIMEI					[29] IMEI OPTIONAL,
	rATType						[30] RATType OPTIONAL,
	sGWChange					[34] SGWChange OPTIONAL,
	p-GWAddressUsed				[36] GSNAddress OPTIONAL,
	p-GWPLMNIdentifier			[37] PLMN-Id OPTIONAL,
	startTime					[38] TimeStamp OPTIONAL,
	stopTime					[39] TimeStamp OPTIONAL,
	pDNConnectionChargingID		[40] ChargingID OPTIONAL,
	servedPDPPDNAddressExt 		[43] PDPAddress OPTIONAL,
	dynamicAddressFlagExt		[47] DynamicAddressFlag OPTIONAL,
	tWAGiPv6AddressUsed			[48] GSNAddress OPTIONAL,
	p-GWiPv6AddressUsed			[50] GSNAddress OPTIONAL,
	retransmission				[51] NULL OPTIONAL,
	enhancedDiagnostics			[52] EnhancedDiagnostics OPTIONAL,
	tWANUserLocationInformation	[53] TWANUserLocationInfo OPTIONAL,
	iMSIunauthenticatedFlag 	[54] NULL OPTIONAL
}

SGSNMMRecord	::= SET
{
	recordType					[0] RecordType,
	servedIMSI					[1] IMSI,
	servedIMEI					[2] IMEI OPTIONAL,
	sgsnAddress					[3] GSNAddress OPTIONAL,
	msNetworkCapability			[4] MSNetworkCapability OPTIONAL,
	routingArea					[5] RoutingAreaCode OPTIONAL,
	locationAreaCode			[6] LocationAreaCode OPTIONAL,
	cellIdentifier				[7] CellId OPTIONAL,
	changeLocation				[8] SEQUENCE OF ChangeLocation OPTIONAL,
	recordOpeningTime			[9] TimeStamp,
	duration					[10] CallDuration OPTIONAL,
	sgsnChange					[11] SGSNChange OPTIONAL,
	causeForRecClosing			[12] CauseForRecClosing,
	diagnostics					[13] Diagnostics OPTIONAL,
	recordSequenceNumber		[14] INTEGER OPTIONAL,
	nodeID						[15] NodeID OPTIONAL,
	recordExtensions			[16] ManagementExtensions OPTIONAL,
	localSequenceNumber			[17] LocalSequenceNumber OPTIONAL,
	servedMSISDN				[18] MSISDN OPTIONAL,
	chargingCharacteristics		[19] ChargingCharacteristics,
	cAMELInformationMM 			[20] CAMELInformationMM OPTIONAL,
	rATType						[21] RATType OPTIONAL,
	chChSelectionMode			[22] ChChSelectionMode OPTIONAL,
	cellPLMNId					[23] PLMN-Id OPTIONAL,
	servingNodePLMNIdentifier	[24] PLMN-Id OPTIONAL,
	cNOperatorSelectionEnt		[25] CNOperatorSelectionEntity OPTIONAL
}

SGSNPDPRecord 	::= SET
{
	recordType					[0] RecordType,
	networkInitiation			[1] NetworkInitiatedPDPContext OPTIONAL,
	servedIMSI					[3] IMSI OPTIONAL,
	servedIMEI					[4] IMEI OPTIONAL,
	sgsnAddress					[5] GSNAddress OPTIONAL,
	msNetworkCapability			[6] MSNetworkCapability OPTIONAL,
	routingArea					[7] RoutingAreaCode OPTIONAL,
	locationAreaCode			[8] LocationAreaCode OPTIONAL,
	cellIdentifier				[9] CellId OPTIONAL,
	chargingID					[10] ChargingID,
	ggsnAddressUsed				[11] GSNAddress,
	accessPointNameNI			[12] AccessPointNameNI OPTIONAL,
	pdpType						[13] PDPType OPTIONAL,
	servedPDPAddress			[14] PDPAddress OPTIONAL,
	listOfTrafficVolumes		[15] SEQUENCE OF ChangeOfCharCondition OPTIONAL,
	recordOpeningTime			[16] TimeStamp,
	duration					[17] CallDuration,
	sgsnChange					[18] SGSNChange OPTIONAL,
	causeForRecClosing			[19] CauseForRecClosing,
	diagnostics					[20] Diagnostics OPTIONAL,
	recordSequenceNumber		[21] INTEGER OPTIONAL,
	nodeID						[22] NodeID OPTIONAL,
	recordExtensions			[23] ManagementExtensions OPTIONAL,
	localSequenceNumber			[24] LocalSequenceNumber OPTIONAL,
	apnSelectionMode			[25] APNSelectionMode OPTIONAL,
	accessPointNameOI			[26] AccessPointNameOI OPTIONAL,
	servedMSISDN				[27] MSISDN OPTIONAL,
	chargingCharacteristics		[28] ChargingCharacteristics,
	rATType						[29] RATType OPTIONAL,
	cAMELInformationPDP  		[30] CAMELInformationPDP OPTIONAL,
	rNCUnsentDownlinkVolume		[31] DataVolumeGPRS OPTIONAL,
	chChSelectionMode			[32] ChChSelectionMode OPTIONAL,
	dynamicAddressFlag			[33] DynamicAddressFlag OPTIONAL,
	iMSIunauthenticatedFlag 	[34] NULL OPTIONAL,
	userCSGInformation			[35] UserCSGInformation OPTIONAL,
	servedPDPPDNAddressExt 		[36] PDPAddress OPTIONAL,
	lowPriorityIndicator		[37] NULL OPTIONAL,
	servingNodePLMNIdentifier	[38] PLMN-Id OPTIONAL,
	cNOperatorSelectionEnt		[39] CNOperatorSelectionEntity OPTIONAL
}

SGSNSMORecord	::= SET
--
--   also for MME UE originated SMS record
--
{
	recordType					[0] RecordType,
	servedIMSI					[1] IMSI,
	servedIMEI					[2] IMEI OPTIONAL,
	servedMSISDN				[3] MSISDN OPTIONAL,
	msNetworkCapability			[4] MSNetworkCapability OPTIONAL,
	serviceCentre				[5] AddressString OPTIONAL,
	recordingEntity				[6] RecordingEntity OPTIONAL,
	locationArea				[7] LocationAreaCode OPTIONAL,
	routingArea					[8] RoutingAreaCode OPTIONAL,
	cellIdentifier				[9] CellId OPTIONAL,
	messageReference			[10] MessageReference,
	eventTimeStamp				[11] TimeStamp,
	smsResult					[12] SMSResult OPTIONAL,
	recordExtensions			[13] ManagementExtensions OPTIONAL,
	nodeID						[14] NodeID OPTIONAL,
	localSequenceNumber			[15] LocalSequenceNumber OPTIONAL,
	chargingCharacteristics		[16] ChargingCharacteristics,
	rATType						[17] RATType OPTIONAL,
	destinationNumber			[18] SmsTpDestinationNumber OPTIONAL,
	cAMELInformationSMS			[19] CAMELInformationSMS OPTIONAL,
	chChSelectionMode			[20] ChChSelectionMode OPTIONAL,
	servingNodeType				[21] ServingNodeType,
	servingNodeAddress			[22] GSNAddress OPTIONAL,
	servingNodeiPv6Address		[23] GSNAddress OPTIONAL,
	mMEName						[24] DiameterIdentity OPTIONAL,
	mMERealm					[25] DiameterIdentity OPTIONAL,
	userLocationInformation		[26] OCTET STRING OPTIONAL,
	retransmission				[27] NULL OPTIONAL,
	servingNodePLMNIdentifier	[28] PLMN-Id OPTIONAL,
	userLocationInfoTime		[29] TimeStamp OPTIONAL,
	cNOperatorSelectionEnt		[30] CNOperatorSelectionEntity OPTIONAL
}

SGSNSMTRecord	::= SET
--
--   also for MME UE terminated SMS record
--
{
	recordType					 [0] RecordType,
	servedIMSI					 [1] IMSI,
	servedIMEI					 [2] IMEI OPTIONAL,
	servedMSISDN				 [3] MSISDN OPTIONAL,
	msNetworkCapability			 [4] MSNetworkCapability OPTIONAL,
	serviceCentre				 [5] AddressString OPTIONAL,
	recordingEntity				 [6] RecordingEntity OPTIONAL,
	locationArea				 [7] LocationAreaCode OPTIONAL,
	routingArea					 [8] RoutingAreaCode OPTIONAL,
	cellIdentifier				 [9] CellId OPTIONAL,
	eventTimeStamp				 [10] TimeStamp,
	smsResult					 [11] SMSResult OPTIONAL,
	recordExtensions			 [12] ManagementExtensions OPTIONAL,
	nodeID						 [13] NodeID OPTIONAL,
	localSequenceNumber			 [14] LocalSequenceNumber OPTIONAL,
	chargingCharacteristics		 [15] ChargingCharacteristics,
	rATType						 [16] RATType OPTIONAL,
	chChSelectionMode			 [17] ChChSelectionMode OPTIONAL,
	cAMELInformationSMS			 [18] CAMELInformationSMS OPTIONAL,
	originatingAddress			 [19] AddressString OPTIONAL,
	servingNodeType				 [20] ServingNodeType,
	servingNodeAddress			 [21] GSNAddress OPTIONAL,
	servingNodeiPv6Address		 [22] GSNAddress OPTIONAL,
	mMEName						 [23] DiameterIdentity OPTIONAL,
	mMERealm					 [24] DiameterIdentity OPTIONAL,
	userLocationInformation		 [25] OCTET STRING OPTIONAL,
	retransmission				 [26] NULL OPTIONAL,
	servingNodePLMNIdentifier	 [27] PLMN-Id OPTIONAL,
	userLocationInfoTime		 [28] TimeStamp OPTIONAL,
	cNOperatorSelectionEnt		 [29] CNOperatorSelectionEntity OPTIONAL
}

SGSNMTLCSRecord			::= SET
{
	recordType					 [0] RecordType,
	recordingEntity				 [1] RecordingEntity,
	lcsClientType				 [2] LCSClientType,
	lcsClientIdentity			 [3] LCSClientIdentity,
	servedIMSI					 [4] IMSI,
	servedMSISDN				 [5] MSISDN OPTIONAL,
	sgsnAddress					 [6] GSNAddress OPTIONAL,
	locationType				 [7] LocationType,
	lcsQos						 [8] LCSQoSInfo OPTIONAL,
	lcsPriority					 [9] LCS-Priority OPTIONAL,
	mlcNumber					 [10] ISDN-AddressString,
	eventTimeStamp				 [11] TimeStamp,
	measurementDuration			 [12] CallDuration OPTIONAL,
	notificationToMSUser		 [13] NotificationToMSUser OPTIONAL,
	privacyOverride				 [14] NULL OPTIONAL,
	location					 [15] LocationAreaAndCell OPTIONAL,
	routingArea					 [16] RoutingAreaCode OPTIONAL,
	locationEstimate			 [17] Ext-GeographicalInformation OPTIONAL,
	positioningData				 [18] PositioningData OPTIONAL,
	lcsCause					 [19] LCSCause OPTIONAL,
	diagnostics					 [20] Diagnostics OPTIONAL,
	nodeID						 [21] NodeID OPTIONAL,
	localSequenceNumber			 [22] LocalSequenceNumber OPTIONAL,
	chargingCharacteristics		 [23] ChargingCharacteristics,
	chChSelectionMode			 [24] ChChSelectionMode OPTIONAL,
	rATType						 [25] RATType OPTIONAL,
	recordExtensions			 [26] ManagementExtensions OPTIONAL,
	causeForRecClosing			 [27] CauseForRecClosing,
	servingNodePLMNIdentifier	 [28] PLMN-Id OPTIONAL,
	cNOperatorSelectionEnt		 [29] CNOperatorSelectionEntity OPTIONAL
}

SGSNMOLCSRecord			::= SET
{
	recordType					 [0] RecordType,
	recordingEntity				 [1] RecordingEntity,
	lcsClientType				 [2] LCSClientType OPTIONAL,
	lcsClientIdentity			 [3] LCSClientIdentity OPTIONAL,
	servedIMSI					 [4] IMSI,
	servedMSISDN				 [5] MSISDN OPTIONAL,
	sgsnAddress					 [6] GSNAddress OPTIONAL,
	locationMethod				 [7] LocationMethod,
	lcsQos						 [8] LCSQoSInfo OPTIONAL,
	lcsPriority					 [9] LCS-Priority OPTIONAL,
	mlcNumber					 [10] ISDN-AddressString OPTIONAL,
	eventTimeStamp				 [11] TimeStamp,
	measurementDuration			 [12] CallDuration OPTIONAL,
	location					 [13] LocationAreaAndCell OPTIONAL,
	routingArea					 [14] RoutingAreaCode OPTIONAL,
	locationEstimate			 [15] Ext-GeographicalInformation OPTIONAL,
	positioningData				 [16] PositioningData OPTIONAL,
	lcsCause					 [17] LCSCause OPTIONAL,
	diagnostics					 [18] Diagnostics OPTIONAL,
	nodeID						 [19] NodeID OPTIONAL,
	localSequenceNumber			 [20] LocalSequenceNumber OPTIONAL,
	chargingCharacteristics		 [21] ChargingCharacteristics,
	chChSelectionMode			 [22] ChChSelectionMode OPTIONAL,
	rATType						 [23] RATType OPTIONAL,
	recordExtensions			 [24] ManagementExtensions OPTIONAL,
	causeForRecClosing			 [25] CauseForRecClosing,
	servingNodePLMNIdentifier	 [26] PLMN-Id OPTIONAL,
	cNOperatorSelectionEnt		 [27] CNOperatorSelectionEntity OPTIONAL
}

SGSNNILCSRecord			::= SET
{
	recordType					 [0] RecordType,
	recordingEntity				 [1] RecordingEntity,
	lcsClientType				 [2] LCSClientType OPTIONAL,
	lcsClientIdentity			 [3] LCSClientIdentity OPTIONAL,
	servedIMSI					 [4] IMSI OPTIONAL,
	servedMSISDN				 [5] MSISDN OPTIONAL,
	sgsnAddress					 [6] GSNAddress OPTIONAL,
	servedIMEI					 [7] IMEI OPTIONAL,
	lcsQos						 [8] LCSQoSInfo OPTIONAL,
	lcsPriority					 [9] LCS-Priority OPTIONAL,
	mlcNumber					 [10] ISDN-AddressString OPTIONAL,
	eventTimeStamp				 [11] TimeStamp,
	measurementDuration			 [12] CallDuration OPTIONAL,
	location					 [13] LocationAreaAndCell OPTIONAL,
	routingArea					 [14] RoutingAreaCode OPTIONAL,
	locationEstimate			 [15] Ext-GeographicalInformation OPTIONAL,
	positioningData				 [16] PositioningData OPTIONAL,
	lcsCause					 [17] LCSCause OPTIONAL,
	diagnostics					 [18] Diagnostics OPTIONAL,
	nodeID						 [19] NodeID OPTIONAL,
	localSequenceNumber			 [20] LocalSequenceNumber OPTIONAL,
	chargingCharacteristics		 [21] ChargingCharacteristics,
	chChSelectionMode			 [22] ChChSelectionMode OPTIONAL,
	rATType						 [23] RATType OPTIONAL,
	recordExtensions			 [24] ManagementExtensions OPTIONAL,
	causeForRecClosing			 [25] CauseForRecClosing,
	servingNodePLMNIdentifier	 [26] PLMN-Id OPTIONAL,
	cNOperatorSelectionEnt		 [27] CNOperatorSelectionEntity OPTIONAL
}

SGSNMBMSRecord	::= SET
{
	recordType					[0] RecordType,
	ggsnAddress					[1] GSNAddress,
	chargingID					[2] ChargingID,
	listofRAs					[3] SEQUENCE OF RAIdentity OPTIONAL,
	accessPointNameNI			[4] AccessPointNameNI OPTIONAL,
	servedPDPAddress			[5] PDPAddress OPTIONAL,
	listOfTrafficVolumes		[6] SEQUENCE OF ChangeOfMBMSCondition OPTIONAL,
	recordOpeningTime			[7] TimeStamp,
	duration					[8] CallDuration,
	causeForRecClosing			[9] CauseForRecClosing,
	diagnostics					[10] Diagnostics OPTIONAL,
	recordSequenceNumber		[11] INTEGER OPTIONAL,
	nodeID						[12] NodeID OPTIONAL,
	recordExtensions			[13] ManagementExtensions OPTIONAL,
	localSequenceNumber			[14] LocalSequenceNumber OPTIONAL,
	sgsnPLMNIdentifier			[15] PLMN-Id OPTIONAL,
	numberofReceivingUE			[16] INTEGER OPTIONAL,
	mbmsInformation				[17] MBMSInformation OPTIONAL
}

GGSNMBMSRecord	::= SET
{
	recordType					[0] RecordType,
	ggsnAddress					[1] GSNAddress,
	chargingID					[2] ChargingID,
	listofDownstreamNodes		[3] SEQUENCE OF GSNAddress,
	accessPointNameNI			[4] AccessPointNameNI OPTIONAL,
	servedPDPAddress			[5] PDPAddress OPTIONAL,
	listOfTrafficVolumes		[6] SEQUENCE OF ChangeOfMBMSCondition OPTIONAL,
	recordOpeningTime			[7] TimeStamp,
	duration					[8] CallDuration,
	causeForRecClosing			[9] CauseForRecClosing,
	diagnostics					[10] Diagnostics OPTIONAL,
	recordSequenceNumber		[11] INTEGER OPTIONAL,
	nodeID						[12] NodeID OPTIONAL,
	recordExtensions			[13] ManagementExtensions OPTIONAL,
	localSequenceNumber			[14] LocalSequenceNumber OPTIONAL,
	mbmsInformation				[15] MBMSInformation OPTIONAL
}

GWMBMSRecord	::= SET
{
	recordType					[0] RecordType,
	mbmsGWAddress				[1] GSNAddress,
	chargingID					[2] ChargingID,
	listofDownstreamNodes		[3] SEQUENCE OF GSNAddress,
	accessPointNameNI			[4] AccessPointNameNI OPTIONAL,
	pdpPDNType					[5] PDPType OPTIONAL,
	servedPDPPDNAddress			[6] PDPAddress OPTIONAL,
	listOfTrafficVolumes		[7] SEQUENCE OF ChangeOfMBMSCondition OPTIONAL,
	recordOpeningTime			[8] TimeStamp,
	duration					[9] CallDuration,
	causeForRecClosing			[10] CauseForRecClosing,
	diagnostics					[11] Diagnostics OPTIONAL,
	recordSequenceNumber		[12] INTEGER OPTIONAL,
	nodeID						[13] NodeID OPTIONAL,
	recordExtensions			[14] ManagementExtensions OPTIONAL,
	localSequenceNumber			[15] LocalSequenceNumber OPTIONAL,
	mbmsInformation				[16] MBMSInformation OPTIONAL,
	commonTeid   				[17] CTEID OPTIONAL,
	iPMulticastSourceAddress	[18] PDPAddress OPTIONAL
}

--
--  PS DATA TYPES
--


AccessAvailabilityChangeReason		::= INTEGER (0..4294967295)
--
-- 0 (RAN rule indication)   : This value shall be used to indicate that the availability
--                             of an access is changed due to the RAN rule indication.
-- 1 (Access usable/unusable): This value shall be used to indicate that the availability
--                             of an access is changed due to the access is unusable or usable
--                             again.
--

AccessLineIdentifier	::= SEQUENCE
--
-- "Physical Access Id" includes a port identifier and the identity of the access node where the
--  port resides. "logical Access Id" contains a Circuit-ID. Both are defined ETSI TS 283 034 [314]
--
{
	physicalAccessID	[0] UTF8String OPTIONAL,
	logicalAccessID		[1] OCTET STRING OPTIONAL
}

AccessPointNameNI	::= IA5String (SIZE(1..63))
--
-- Network Identifier part of APN in  dot representation.
-- For example, if the complete APN is 'apn1a.apn1b.apn1c.mnc022.mcc111.gprs'
-- NI is 'apn1a.apn1b.apn1c' and is presented in this form in the CDR.
--

AccessPointNameOI	::= IA5String (SIZE(1..37))
--
-- Operator Identifier part of APN in dot representation.
-- In the 'apn1a.apn1b.apn1c.mnc022.mcc111.gprs' example, the OI portion is 'mnc022.mcc111.gprs'
-- and is presented in this form in the CDR.
--

ADCRuleBaseName		::= IA5String
--
-- identifier for the group of charging rules
-- see ADC-Rule-Base-Name AVP as desined in TS 29.212 [220]
--
AdditionalExceptionReports		::= ENUMERATED
{
	notAllowed		(0),
	allowed			(1)
}


AFChargingIdentifier	::= OCTET STRING
--
-- see AF-Charging-Identifier AVP as defined in TS 29.214[221]
--
AFRecordInformation	::= SEQUENCE
{
	aFChargingIdentifier		[1] AFChargingIdentifier,
	flows						[2] Flows OPTIONAL
}


APNRateControl		::= SEQUENCE
--
-- See TS 24.008 [208] for more information
--
{
	aPNRateControlUplink	[0] APNRateControlParameters OPTIONAL,
	aPNRateControlDownlink	[1] APNRateControlParameters OPTIONAL
}

APNRateControlParameters		::= SEQUENCE
{
	additionalExceptionReports	[0] AdditionalExceptionReports OPTIONAL,
	rateControlTimeUnit			[1] RateControlTimeUnit OPTIONAL,
	rateControlMaxRate			[2] INTEGER OPTIONAL,
	rateControlMaxMessageSize	[3] DataVolumeGPRS OPTIONAL -- aPNRateControlDownlink only
}


APNSelectionMode	::= ENUMERATED
--
-- See Information Elements TS 29.060 [215], TS 29.274 [223] or TS 29.275 [224]
--
{
	mSorNetworkProvidedSubscriptionVerified				(0),
	mSProvidedSubscriptionNotVerified					(1),
	networkProvidedSubscriptionNotVerified				(2)
}

CalleePartyInformation	::= SEQUENCE
{
called-Party-Address				[0] InvolvedParty OPTIONAL,
requested-Party-Address				[1] InvolvedParty OPTIONAL,
list-Of-Called-Asserted-Identity 	[2] SEQUENCE OF InvolvedParty OPTIONAL
}

CAMELAccessPointNameNI	::= AccessPointNameNI

CAMELAccessPointNameOI	::= AccessPointNameOI

CAMELInformationMM		::= SET
{
	sCFAddress						[1] SCFAddress OPTIONAL,
	serviceKey						[2] ServiceKey OPTIONAL,
	defaultTransactionHandling		[3] DefaultGPRS-Handling OPTIONAL,
	numberOfDPEncountered  			[4] NumberOfDPEncountered OPTIONAL,
	levelOfCAMELService				[5] LevelOfCAMELService OPTIONAL,
	freeFormatData					[6] FreeFormatData OPTIONAL,
	fFDAppendIndicator				[7] FFDAppendIndicator OPTIONAL
}

CAMELInformationPDP	::= SET
{
	sCFAddress						[1] SCFAddress OPTIONAL,
	serviceKey						[2] ServiceKey OPTIONAL,
	defaultTransactionHandling		[3] DefaultGPRS-Handling OPTIONAL,
	cAMELAccessPointNameNI			[4] CAMELAccessPointNameNI OPTIONAL,
	cAMELAccessPointNameOI			[5] CAMELAccessPointNameOI OPTIONAL,
	numberOfDPEncountered			[6] NumberOfDPEncountered OPTIONAL,
	levelOfCAMELService				[7] LevelOfCAMELService OPTIONAL,
	freeFormatData					[8] FreeFormatData OPTIONAL,
	fFDAppendIndicator				[9] FFDAppendIndicator OPTIONAL
}

CAMELInformationSMS		::= SET
{
	sCFAddress								[1] SCFAddress OPTIONAL,
	serviceKey								[2] ServiceKey OPTIONAL,
	defaultSMSHandling						[3] DefaultSMS-Handling OPTIONAL,
	cAMELCallingPartyNumber					[4] CallingNumber OPTIONAL,
	cAMELDestinationSubscriberNumber		[5] SmsTpDestinationNumber OPTIONAL,
	cAMELSMSCAddress						[6] AddressString OPTIONAL,
	freeFormatData							[7] FreeFormatData OPTIONAL,
	smsReferenceNumber						[8] CallReferenceNumber	OPTIONAL
}

ChangeCondition	::= ENUMERATED
{
	qoSChange						(0),
	tariffTime						(1),
	recordClosure					(2),
	cGI-SAICHange					(6),	-- bearer modification. "CGI-SAI Change"
	rAIChange						(7),	-- bearer modification. "RAI Change"
	dT-Establishment				(8),
	dT-Removal						(9),
	eCGIChange						(10),	-- bearer modification. "ECGI Change"
	tAIChange						(11),	-- bearer modification. "TAI Change"
	userLocationChange				(12),	-- bearer modification. "User Location Change"
	userCSGInformationChange		(13), 	-- bearer modification. "User CSG info Change"
	presenceInPRAChange				(14),	-- bearer modification. "Change of UE Presence
													-- in Presence Reporting Area"
	removalOfAccess					(15),	-- NBIFOM "Removal of Access"
	unusabilityOfAccess				(16),	-- NBIFOM "Unusability of Access"
	indirectChangeCondition			(17),	-- NBIFOM "Indirect Change Condition"
	userPlaneToUEChange				(18),	-- bearer modification. "Change of user plane to UE"
	servingPLMNRateControlChange	(19),
-- bearer modification "Serving PLMN Rate Control Change"
	threeGPPPSDataOffStatusChange	(20),   -- "Change of 3GPP PS DataO ff Status"
	aPNRateControlChange			(21)	-- bearer modification. "APN Rate ControlChange"


}

ChangeOfCharCondition	::= SEQUENCE
--
-- qosRequested and qosNegotiated are used in S-CDR only
-- ePCQoSInformation used in SGW-CDR,PGW-CDR, IPE-CDR, TWAG-CDR and ePDG-CDR only
-- userLocationInformation is used only in S-CDR, SGW-CDR and PGW-CDR
-- chargingID used in PGW-CDR only when Charging per IP-CAN session is active
-- accessAvailabilityChangeReason and relatedChangeOfCharCondition applicable only in PGW-CDR
-- cPCIoTOptimisationIndicator is used in SGW-CDR only
-- aPNRateControl is valid for PGW-CDR only

--
{
	qosRequested					[1] QoSInformation OPTIONAL,
	qosNegotiated							[2] QoSInformation OPTIONAL,
	dataVolumeGPRSUplink					[3] DataVolumeGPRS OPTIONAL,
	dataVolumeGPRSDownlink					[4] DataVolumeGPRS OPTIONAL,
	changeCondition							[5] ChangeCondition,
	changeTime								[6] TimeStamp,
	userLocationInformation					[8] OCTET STRING OPTIONAL,
	ePCQoSInformation						[9] EPCQoSInformation OPTIONAL,
	chargingID								[10] ChargingID OPTIONAL,
	presenceReportingAreaStatus 			[11] PresenceReportingAreaStatus OPTIONAL,
	userCSGInformation						[12] UserCSGInformation OPTIONAL,
	diagnostics								[13] Diagnostics OPTIONAL,
	enhancedDiagnostics						[14] EnhancedDiagnostics OPTIONAL,
	rATType									[15] RATType OPTIONAL,
	accessAvailabilityChangeReason			[16] AccessAvailabilityChangeReason OPTIONAL,
	uWANUserLocationInformation				[17] UWANUserLocationInfo OPTIONAL,
	relatedChangeOfCharCondition			[18] RelatedChangeOfCharCondition OPTIONAL,
	cPCIoTEPSOptimisationIndicator			[19] CPCIoTEPSOptimisationIndicator OPTIONAL,
	servingPLMNRateControl					[20] ServingPLMNRateControl OPTIONAL,
	threeGPPPSDataOffStatus					[21] ThreeGPPPSDataOffStatus OPTIONAL,
	listOfPresenceReportingAreaInformation	[22] SEQUENCE OF PresenceReportingAreaInfo OPTIONAL,
	aPNRateControl							[23] APNRateControl OPTIONAL


}

ChangeOfMBMSCondition	::= SEQUENCE
--
-- Used in MBMS record
--
{
	qosRequested				[1] QoSInformation OPTIONAL,
	qosNegotiated				[2] QoSInformation OPTIONAL,
	dataVolumeMBMSUplink		[3] DataVolumeMBMS OPTIONAL,
	dataVolumeMBMSDownlink		[4] DataVolumeMBMS,
	changeCondition				[5] ChangeCondition,
	changeTime					[6] TimeStamp,
	failureHandlingContinue		[7] FailureHandlingContinue OPTIONAL
}

ChangeOfServiceCondition	::= SEQUENCE
--
-- Used for Flow based Charging and Application based Charging service data container
-- presenceReportingAreaStatus is used in PGW-CDR Only
--
{
	ratingGroup 						[1] RatingGroupId,
	chargingRuleBaseName				[2] ChargingRuleBaseName OPTIONAL,
	resultCode							[3] ResultCode OPTIONAL,
	localSequenceNumber					[4] LocalSequenceNumber OPTIONAL,
	timeOfFirstUsage					[5] TimeStamp OPTIONAL,
	timeOfLastUsage						[6] TimeStamp OPTIONAL,
	timeUsage 							[7] CallDuration OPTIONAL,
	serviceConditionChange				[8] ServiceConditionChange,
	qoSInformationNeg					[9] EPCQoSInformation OPTIONAL,
	servingNodeAddress 					[10] GSNAddress OPTIONAL,
	datavolumeFBCUplink					[12] DataVolumeGPRS OPTIONAL,
	datavolumeFBCDownlink				[13] DataVolumeGPRS OPTIONAL,
	timeOfReport						[14] TimeStamp,
	failureHandlingContinue				[16] FailureHandlingContinue OPTIONAL,
	serviceIdentifier					[17] ServiceIdentifier OPTIONAL,
	pSFurnishChargingInformation		[18] PSFurnishChargingInformation OPTIONAL,
	aFRecordInformation					[19] SEQUENCE OF AFRecordInformation OPTIONAL,
	userLocationInformation				[20] OCTET STRING OPTIONAL,
	eventBasedChargingInformation		[21] EventBasedChargingInformation OPTIONAL,
	timeQuotaMechanism					[22] TimeQuotaMechanism OPTIONAL,
	serviceSpecificInfo					[23] SEQUENCE OF ServiceSpecificInfo OPTIONAL,
	threeGPP2UserLocationInformation	[24] OCTET STRING OPTIONAL,
	sponsorIdentity						[25] OCTET STRING OPTIONAL,
	applicationServiceProviderIdentity	[26] OCTET STRING OPTIONAL,
	aDCRuleBaseName						[27] ADCRuleBaseName OPTIONAL,
	presenceReportingAreaStatus 		[28] PresenceReportingAreaStatus OPTIONAL,
	userCSGInformation					[29] UserCSGInformation OPTIONAL,
	rATType								[30] RATType OPTIONAL,
	uWANUserLocationInformation			[32] UWANUserLocationInfo OPTIONAL,
	relatedChangeOfServiceCondition		[33] RelatedChangeOfServiceCondition OPTIONAL,
	servingPLMNRateControl				[35] ServingPLMNRateControl OPTIONAL,
	aPNRateControl						[36] APNRateControl OPTIONAL,
	threeGPPPSDataOffStatus             [37] ThreeGPPPSDataOffStatus OPTIONAL,
	trafficSteeringPolicyIDDownlink     [38] TrafficSteeringPolicyIDDownlink OPTIONAL,
trafficSteeringPolicyIDUplink       [39] TrafficSteeringPolicyIDUplink OPTIONAL,
	tWANUserLocationInformation			[40] TWANUserLocationInfo OPTIONAL,
	listOfPresenceReportingAreaInformation	[41] SEQUENCE OF PresenceReportingAreaInfo OPTIONAL,
	voLTEInformation						[42] VoLTEInformation OPTIONAL

}

ChangeLocation	::= SEQUENCE
--
-- used in SGSNMMRecord only
--
{
	locationAreaCode		[0] LocationAreaCode,
	routingAreaCode			[1] RoutingAreaCode,
	cellId					[2] CellId OPTIONAL,
	changeTime				[3] TimeStamp,
	mCC-MNC					[4] PLMN-Id OPTIONAL
}

ChargingCharacteristics	::= OCTET STRING (SIZE(2))


ChargingPerIPCANSessionIndicator	::= ENUMERATED
{
	inactive		(0),
	active               (1)
}

ChargingRuleBaseName	::= IA5String
--
-- identifier for the group of charging rules
-- see Charging-Rule-Base-Name AVP as desined in TS 29.212 [220]
--

ChChSelectionMode		::= ENUMERATED
{
	servingNodeSupplied			(0),	-- For S-GW/P-GW
	subscriptionSpecific		(1),	-- For SGSN only
	aPNSpecific					(2),	-- For SGSN only
	homeDefault					(3),	-- For SGSN, S-GW, P-GW, TDF and IP-Edge
	roamingDefault				(4),	-- For SGSN, S-GW, P-GW, TDF and IP-Edge
	visitingDefault				(5),	-- For SGSN, S-GW, P-GW, TDF and IP-Edge
	fixedDefault				(6)		-- For TDF and IP-Edge
}

CNOperatorSelectionEntity	::= ENUMERATED
{
	servCNSelectedbyUE		(0),
	servCNSelectedbyNtw		(1)
}

CPCIoTEPSOptimisationIndicator ::= BOOLEAN

CSGAccessMode		::= ENUMERATED
{
	closedMode  (0),
	hybridMode  (1)
}

CSGId		::= OCTET STRING (SIZE(4))
--
-- Defined in TS 23.003 [200]. Coded according to TS 29.060 [215] for GTP, and
-- in TS 29.274 [223] for eGTP.
--

CTEID		::= OCTET STRING (SIZE(4))
--
-- Defined in TS 32.251[11] for MBMS-GW-CDR. Common Tunnel Endpoint Identifier
-- of MBMS GW for user plane, defined in TS 23.246 [207].
--

DataVolumeGPRS		::= INTEGER
--
-- The volume of data transferred in octets.
--

DataVolumeMBMS ::= INTEGER
--
-- The volume of data transferred in octets.
--


EPCQoSInformation	::= SEQUENCE
--
-- See TS 29.212 [220] for more information
--
{
	qCI							[1] INTEGER,
	maxRequestedBandwithUL		[2] INTEGER OPTIONAL,
	maxRequestedBandwithDL		[3] INTEGER OPTIONAL,
	guaranteedBitrateUL			[4] INTEGER OPTIONAL,
	guaranteedBitrateDL			[5] INTEGER OPTIONAL,
	aRP							[6] INTEGER OPTIONAL,
	aPNAggregateMaxBitrateUL	[7] INTEGER OPTIONAL,
	aPNAggregateMaxBitrateDL	[8] INTEGER OPTIONAL,
	extendedMaxRequestedBWUL	[9] INTEGER OPTIONAL,
	extendedMaxRequestedBWDL	[10] INTEGER OPTIONAL,
	extendedGBRUL				[11] INTEGER OPTIONAL,
	extendedGBRDL				[12] INTEGER OPTIONAL,
	extendedAPNAMBRUL			[13] INTEGER OPTIONAL,
	extendedAPNAMBRDL			[14] INTEGER OPTIONAL
}

EventBasedChargingInformation		::= SEQUENCE
{
	numberOfEvents		[1] INTEGER,
	eventTimeStamps  	[2] SEQUENCE OF TimeStamp OPTIONAL
}

FailureHandlingContinue		::= BOOLEAN
--
-- This parameter is included when the failure handling procedure has been executed and new
-- containers are opened. This parameter shall be included in the first and subsequent
-- containers opened after the failure handling execution.
--

FFDAppendIndicator	::= BOOLEAN


FixedSubsID	::= OCTET STRING
--
-- The fixed subscriber Id identifier is defined in Broadband Forum TR 134 [601].
--


FixedUserLocationInformation	::= SEQUENCE
--
-- See format in IEEE Std 802.11-2012 [408] for "SSID" and "BSSID".
--
{
	sSID					[0] OCTET STRING OPTIONAL ,
	bSSID					[1] OCTET STRING OPTIONAL,
	accessLineIdentifier	[2] AccessLineIdentifier OPTIONAL
}

Flows		::= 	SEQUENCE
--
-- See Flows AVP as defined in TS 29.214 [221]
--
{
	mediaComponentNumber	[1] INTEGER,
	flowNumber  			[2] SEQUENCE OF INTEGER OPTIONAL
}

FreeFormatData		::=	OCTET STRING (SIZE(1..160))
--
-- Free formatted data as sent in the FurnishChargingInformationGPRS
-- see TS 29.078 [217]
--

-- imported from GenericChargingDataTypes
--GSNAddress		::= IPAddress


MOExceptionDataCounter		::= SEQUENCE
--
-- See TS 29.128 [244] for more information
--
{
	counterValue		[0] INTEGER,
	counterTimestamp	[1] TimeStamp
}


MSNetworkCapability	::= OCTET STRING (SIZE(1..8))
--
-- see TS 24.008 [208]
--

NBIFOMMode		::= ENUMERATED
{
	uEINITIATED				(0),
	nETWORKINITIATED		(1)
}

NBIFOMSupport 	::= ENUMERATED
{
	nBIFOMNotSupported			(0),
	nBIFOMSupported				(1)
}

NetworkInitiatedPDPContext		::= BOOLEAN
--
-- Set to true if PDP context was initiated from network side
--

NumberOfDPEncountered  ::= INTEGER
PDPType		::= OCTET STRING (SIZE(2))
--
-- OCTET 1: PDP Type Organization
-- OCTET 2: PDP/PDN Type Number
-- See TS 29.060 [215] for encoding details.
--


PDPPDNTypeExtension	::= INTEGER
--
-- This integer is 1:1 copy of the PDP type value as defined in TS 29.061 [215].
--


PresenceReportingAreaElementsList ::= OCTET STRING
--
-- For EPC see Presence-Reporting-Area-Elements-List AVP defined in TS 29.212 [220]
-- For 5GC see PresenceInfo defined in TS 29.571 [249] excluding praId and presenceState
--


PresenceReportingAreaInfo	::= SEQUENCE
{
	presenceReportingAreaIdentifier	 [0] OCTET STRING,
	presenceReportingAreaStatus		 [1] PresenceReportingAreaStatus OPTIONAL,
	presenceReportingAreaElementsList[2] PresenceReportingAreaElementsList OPTIONAL,
	presenceReportingAreaNode		 [3] PresenceReportingAreaNode OPTIONAL
}

PresenceReportingAreaNode ::= BIT STRING
{
	oCS   		 (0),
	pCRF  		 (1)
}
--
--	This bit mask has the same format as Presence-Reporting-Area-Node AVP in TS 29.212 [220]
--


PresenceReportingAreaStatus ::= ENUMERATED
{
	insideArea   (0),
	outsideArea  (1),
	inactive 	 (2),
	unknown      (3)

}

PSFurnishChargingInformation		::= SEQUENCE
{
	pSFreeFormatData		[1] FreeFormatData,
	pSFFDAppendIndicator	[2] FFDAppendIndicator OPTIONAL
}

QoSInformation	::= OCTET STRING (SIZE (4..255))
--
-- This  octet string
-- is a 1:1 copy of the contents (i.e. starting with octet 5) of the "Bearer Quality of
-- Service" information element specified in TS 29.274 [223].
--

RANSecondaryRATUsageReport	::= SEQUENCE
--
{
	dataVolumeUplink				[1] DataVolumeGPRS,
	dataVolumeDownlink				[2] DataVolumeGPRS,
	rANStartTime					[3] TimeStamp,
	rANEndTime						[4] TimeStamp,
	secondaryRATType				[5] SecondaryRATType OPTIONAL,
	chargingID						[6] ChargingID OPTIONAL
}


RateControlTimeUnit ::= INTEGER
{	unrestricted	(0),
	minute			(1),
	hour			(2),
	day				(3),
	week			(4)
}

RatingGroupId		::= INTEGER
--
-- IP service flow identity (DCCA), range of 4 byte (0... 4294967295)
-- see Rating-Group AVP as used in TS 32.299 [50]
--

RelatedChangeOfCharCondition	::= SEQUENCE
{
	changeCondition					[5] ChangeCondition,
	changeTime						[6] TimeStamp,
	userLocationInformation			[8] OCTET STRING OPTIONAL,
	presenceReportingAreaStatus 	[11] PresenceReportingAreaStatus OPTIONAL,
	userCSGInformation				[12] UserCSGInformation OPTIONAL,
	rATType							[15] RATType OPTIONAL,
	uWANUserLocationInformation		[17] UWANUserLocationInfo OPTIONAL
}

RelatedChangeOfServiceCondition	::= SEQUENCE
{
	userLocationInformation				[20] OCTET STRING OPTIONAL,
	threeGPP2UserLocationInformation	[24] OCTET STRING OPTIONAL,
	presenceReportingAreaStatus 		[28] PresenceReportingAreaStatus OPTIONAL,
	userCSGInformation					[29] UserCSGInformation OPTIONAL,
	rATType								[30] RATType OPTIONAL,
	uWANUserLocationInformation			[32] UWANUserLocationInfo OPTIONAL,
	relatedServiceConditionChange		[33] ServiceConditionChange OPTIONAL
}

ResultCode		::= INTEGER
--
-- charging protocol return value, range of 4 byte (0... 4294967295)
-- see Result-Code AVP as used in 32.299 [40]
--

SecondaryRATType	::= INTEGER
{
	nR				(0)		-- New Radio 5G
}

ServiceConditionChange	::= BIT STRING
{
	qoSChange 								 (0),	-- bearer modification
	sGSNChange 								 (1),	-- bearer modification:
													-- apply to Gn-SGSN /SGW Change
	sGSNPLMNIDChange 						 (2),	-- bearer modification
	tariffTimeSwitch 						 (3),	-- tariff time change
	pDPContextRelease 						 (4),	-- bearer release
	rATChange 								 (5),	-- bearer modification
	serviceIdledOut 						 (6),	-- IP flow idle out, DCCA QHT expiry
	reserved 								 (7),	-- old: QCTexpiry is no report event
	configurationChange 					 (8),	-- configuration change
	serviceStop 							 (9),	-- IP flow termination.From "Service Stop" in
													-- Change-Condition AVP
	dCCATimeThresholdReached 				(10),	-- DCCA quota reauthorization
	dCCAVolumeThresholdReached 				(11),	-- DCCA quota reauthorization
	dCCAServiceSpecificUnitThresholdReached	(12),	-- DCCA quota reauthorization
	dCCATimeExhausted 						(13),	-- DCCA quota reauthorization
	dCCAVolumeExhausted 					(14),	-- DCCA quota reauthorization
	dCCAValidityTimeout 					(15),	-- DCCA quota validity time (QVT expiry)
	reserved1								(16),	-- reserved due to no use case,
													-- old: return Requested is covered by (17),(18)
	dCCAReauthorisationRequest 				(17),	-- DCCA quota reauthorization request by OCS
	dCCAContinueOngoingSession 				(18),	-- DCCA failure handling (CCFH),
													-- continue IP flow
	dCCARetryAndTerminateOngoingSession		(19),	-- DCCA failure handling (CCFH),
													-- terminate IP flow after DCCA retry
	dCCATerminateOngoingSession 			(20),	-- DCCA failure handling,
													-- terminate IP flow
	cGI-SAIChange							(21),	-- bearer modification. "CGI-SAI Change"
	rAIChange								(22),	-- bearer modification. "RAI Change"
	dCCAServiceSpecificUnitExhausted		(23),	-- DCCA quota reauthorization
	recordClosure							(24),	-- PGW-CDR closure
	timeLimit								(25),	-- intermediate recording. From "Service Data
													--	Time Limit" Change-Condition AVP value
	volumeLimit								(26),	-- intermediate recording.From "Service Data
													--	Volume Limit" Change-Condition AVP value
	serviceSpecificUnitLimit				(27),	-- intermediate recording
	envelopeClosure 						(28),
	eCGIChange								(29),	-- bearer modification. "ECGI Change"
	tAIChange								(30),	-- bearer modification. "TAI Change"
	userLocationChange						(31),	-- bearer modification. "User Location Change"
	userCSGInformationChange				(32),	-- bearer modification. "User CSG info Change"
	presenceInPRAChange						(33), 	-- bearer modification. "Change of UE Presence
													-- in Presence Reporting Area"
	accessChangeOfSDF						(34),	-- "access change of service data flow"
	indirectServiceConditionChange			(35),	-- NBIFOM: "indirect service condition change"
	servingPLMNRateControlChange			(36), 	-- bearer modification. "Serving PLMNRate
												-- Control Change"
	aPNRateControlChange					(37)	-- bearer modification. "APN Rate ControlChange
}
--
-- Trigger and cause values for IP flow level recording are defined for support of independent
-- online and offline charging and also for tight interworking between online and offline charging.
-- Unused bits will always be zero.
-- Some of the values are non-exclusive (e.g. bearer modification reasons).
--

SCFAddress	::= AddressString
--
-- See TS 29.002 [214]
--

ServiceIdentifier	::= INTEGER (0..4294967295)
--
-- The service identifier is used to identify the service or the service component
-- the service data flow relates to. See Service-Identifier AVP as defined in TS 29.212 [220]
--

ServingNodeType	::= ENUMERATED
{
	sGSN		(0),
	pMIPSGW		(1),
	gTPSGW		(2),
	ePDG		(3),
	hSGW		(4),
	mME			(5),
	tWAN		(6)
}


ServingPLMNRateControl		::= SEQUENCE
--
-- See TS 29.128 [244] for more information
--
{
	sPLMNDLRateControlValue	[0] INTEGER,
	sPLMNULRateControlValue	[1] INTEGER
}

SGiPtPTunnellingMethod		::= ENUMERATED
{
	uDPIPbased		(0),
	others			(1)
}


SGSNChange	::= BOOLEAN
--
-- present if first record after inter SGSN routing area update in new SGSN
--

SGWChange		::= BOOLEAN
--
-- present if first record after inter serving node change (SGW, ePDG, TWAG, HSGW)
--


TimeQuotaMechanism		::= SEQUENCE
{
	timeQuotaType					[1] TimeQuotaType,
	baseTimeInterval				[2] INTEGER
}

TimeQuotaType		::= ENUMERATED
{
	dISCRETETIMEPERIOD			(0),
	cONTINUOUSTIMEPERIOD		(1)
}

TrafficSteeringPolicyIDDownlink	::= OCTET STRING
--
-- see Traffic-Steering-Policy-Identifier-DL AVP as defined in TS 29.212[220]

TrafficSteeringPolicyIDUplink	::= OCTET STRING
--
-- see Traffic-Steering-Policy-Identifier-UL AVP as defined in TS 29.212[220]

TWANUserLocationInfo		::= SEQUENCE
{
	sSID					 [0] OCTET STRING,			-- see format in IEEE Std 802.11-2012 [408]
	bSSID					 [1] OCTET STRING OPTIONAL, 	-- see format in IEEE Std 802.11-2012 [408]
	civicAddressInformation	[2] CivicAddressInformation OPTIONAL,
	wLANOperatorId			[3] WLANOperatorId OPTIONAL,
	logicalAccessID			[4] OCTET STRING OPTIONAL
}

UNIPDUCPOnlyFlag	::= BOOLEAN


UserCSGInformation		::= SEQUENCE
{
	cSGId						[0] CSGId,
	cSGAccessMode				[1] CSGAccessMode,
	cSGMembershipIndication		[2] NULL OPTIONAL
}

UWANUserLocationInfo		::= SEQUENCE
{
	uELocalIPAddress		 [0] IPAddress,
	uDPSourcePort			 [1] OCTET STRING (SIZE(2)) OPTIONAL,
	sSID					 [2] OCTET STRING OPTIONAL,	-- see format in IEEE Std 802.11-2012 [408]
	bSSID					 [3] OCTET STRING OPTIONAL,	-- see format in IEEE Std 802.11-2012 [408]
	tCPSourcePort			[4] OCTET STRING (SIZE(2)) OPTIONAL,
	civicAddressInformation	[5] CivicAddressInformation OPTIONAL,
	wLANOperatorId			[6] WLANOperatorId OPTIONAL,
	logicalAccessID			[7] OCTET STRING OPTIONAL
}

VoLTEInformation ::= SEQUENCE
{
	callerInformation	[0] SEQUENCE OF InvolvedParty OPTIONAL,
	calleeInformation	[1] CalleePartyInformation OPTIONAL
}


WLANOperatorId ::= SEQUENCE
{
	wLANOperatorName	[0] OCTET STRING,
	wLANPLMNId			[1] PLMN-Id
}


END

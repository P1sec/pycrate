DSAOperationalAttributeTypes {joint-iso-itu-t ds(5) module(1) dsaOperationalAttributeTypes(22) 8}
DEFINITIONS ::=
BEGIN

-- EXPORTS All 
-- The types and values defined in this module are exported for use in the other ASN.1
-- modules contained within these Directory Specifications, and for the use of other
-- applications which will use them to access Directory services. Other applications may
-- use them for their own purposes, but this will not constrain extensions and
-- modifications needed to maintain or improve the Directory service.

IMPORTS

  -- from Rec. ITU-T X.501 | ISO/IEC 9594-2

  distributedOperations, id-doa, id-kmr, informationFramework,opBindingManagement,
  selectedAttributeTypes
    FROM UsefulDefinitions {joint-iso-itu-t ds(5) module(1) usefulDefinitions(0) 8}

  ATTRIBUTE, MATCHING-RULE, Name
    FROM InformationFramework informationFramework

  OperationalBindingID
    FROM OperationalBindingManagement opBindingManagement

  -- from Rec. ITU-T X.518 | ISO/IEC 9594-4

  AccessPoint, DitBridgeKnowledge, MasterAndShadowAccessPoints
    FROM DistributedOperations distributedOperations

  -- from Rec. ITU-T X.520 | ISO/IEC 9594-6
  bitStringMatch, directoryStringFirstComponentMatch
    FROM SelectedAttributeTypes selectedAttributeTypes ;

dseType ATTRIBUTE ::= {
  WITH SYNTAX             DSEType
  EQUALITY MATCHING RULE  bitStringMatch
  SINGLE VALUE            TRUE
  NO USER MODIFICATION    TRUE
  USAGE                   dSAOperation
  ID                      id-doa-dseType }

DSEType ::= BIT STRING {
  root           (0),  -- root DSE 
  glue           (1),  -- represents knowledge of a name only 
  cp             (2),  -- context prefix 
  entry          (3),  -- object entry 
  alias          (4),  -- alias entry 
  subr           (5),  -- subordinate reference 
  nssr           (6),  -- non-specific subordinate reference 
  supr           (7),  -- superior reference 
  xr             (8),  -- cross reference 
  admPoint       (9),  -- administrative point 
  subentry       (10), -- subentry 
  shadow         (11), -- shadow copy 
  immSupr        (13), -- immediate superior reference 
  rhob           (14), -- rhob information 
  sa             (15), -- subordinate reference to alias entry 
  dsSubentry     (16), -- DSA Specific subentry 
  familyMember   (17), -- family member 
  ditBridge      (18)} -- DIT bridge reference 
--writeableCopy  (19)     writeable copy (currently not used) 

myAccessPoint ATTRIBUTE ::= {
  WITH SYNTAX             AccessPoint
  EQUALITY MATCHING RULE  accessPointMatch
  SINGLE VALUE            TRUE
  NO USER MODIFICATION    TRUE
  USAGE                   dSAOperation
  ID                      id-doa-myAccessPoint }

superiorKnowledge ATTRIBUTE ::= {
  WITH SYNTAX             AccessPoint
  EQUALITY MATCHING RULE  accessPointMatch
  NO USER MODIFICATION    TRUE
  USAGE                   dSAOperation
  ID                      id-doa-superiorKnowledge }

specificKnowledge ATTRIBUTE ::= {
  WITH SYNTAX             MasterAndShadowAccessPoints
  EQUALITY MATCHING RULE  masterAndShadowAccessPointsMatch
  SINGLE VALUE            TRUE
  NO USER MODIFICATION    TRUE
  USAGE                   distributedOperation
  ID                      id-doa-specificKnowledge }

nonSpecificKnowledge ATTRIBUTE ::= {
  WITH SYNTAX             MasterAndShadowAccessPoints
  EQUALITY MATCHING RULE  masterAndShadowAccessPointsMatch
  NO USER MODIFICATION    TRUE
  USAGE                   distributedOperation
  ID                      id-doa-nonSpecificKnowledge }

SupplierOrConsumer ::= SET {
  COMPONENTS OF              AccessPoint, -- supplier or consumer 
  agreementID           [3]  OperationalBindingID,
  ... }

SupplierInformation ::= SET {
  COMPONENTS OF              SupplierOrConsumer, -- supplier 
  supplier-is-master    [4]  BOOLEAN DEFAULT TRUE,
  non-supplying-master  [5]  AccessPoint OPTIONAL,
  ... }

supplierKnowledge ATTRIBUTE ::= {
  WITH SYNTAX             SupplierInformation
  EQUALITY MATCHING RULE  supplierOrConsumerInformationMatch
  NO USER MODIFICATION    TRUE
  USAGE                   dSAOperation
  ID                      id-doa-supplierKnowledge }

ConsumerInformation ::= SupplierOrConsumer -- consumer 

consumerKnowledge ATTRIBUTE ::= {
  WITH SYNTAX             ConsumerInformation
  EQUALITY MATCHING RULE  supplierOrConsumerInformationMatch
  NO USER MODIFICATION    TRUE
  USAGE                   dSAOperation
  ID                      id-doa-consumerKnowledge }

SupplierAndConsumers ::= SET {
  COMPONENTS OF         AccessPoint, -- supplier 
  consumers        [3]  SET OF AccessPoint,
  ... }

secondaryShadows ATTRIBUTE ::= {
  WITH SYNTAX             SupplierAndConsumers
  EQUALITY MATCHING RULE  supplierAndConsumersMatch
  NO USER MODIFICATION    TRUE
  USAGE                   dSAOperation
  ID                      id-doa-secondaryShadows }

ditBridgeKnowledge ATTRIBUTE ::= {
  WITH SYNTAX             DitBridgeKnowledge
  EQUALITY MATCHING RULE  directoryStringFirstComponentMatch
  NO USER MODIFICATION    TRUE
  USAGE                   dSAOperation
  ID                      id-doa-ditBridgeKnowledge }

-- matching rules 

accessPointMatch MATCHING-RULE ::= {
  SYNTAX  Name
  ID      id-kmr-accessPointMatch }

masterAndShadowAccessPointsMatch MATCHING-RULE ::= {
  SYNTAX  SET OF Name
  ID      id-kmr-masterShadowMatch }

supplierOrConsumerInformationMatch MATCHING-RULE ::= {
  SYNTAX SET {
    ae-title              [0]  Name,
    agreement-identifier  [2]  INTEGER}
  ID      id-kmr-supplierConsumerMatch }

supplierAndConsumersMatch MATCHING-RULE ::= {
  SYNTAX  Name
  ID      id-kmr-supplierConsumersMatch }

-- object identifier assignments 

-- dsa operational attributes 

id-doa-dseType                  OBJECT IDENTIFIER ::= {id-doa 0}
id-doa-myAccessPoint            OBJECT IDENTIFIER ::= {id-doa 1}
id-doa-superiorKnowledge        OBJECT IDENTIFIER ::= {id-doa 2}
id-doa-specificKnowledge        OBJECT IDENTIFIER ::= {id-doa 3}
id-doa-nonSpecificKnowledge     OBJECT IDENTIFIER ::= {id-doa 4}
id-doa-supplierKnowledge        OBJECT IDENTIFIER ::= {id-doa 5}
id-doa-consumerKnowledge        OBJECT IDENTIFIER ::= {id-doa 6}
id-doa-secondaryShadows         OBJECT IDENTIFIER ::= {id-doa 7}
id-doa-ditBridgeKnowledge       OBJECT IDENTIFIER ::= {id-doa 8}

-- knowledge matching rules 

id-kmr-accessPointMatch         OBJECT IDENTIFIER ::= {id-kmr 0}
id-kmr-masterShadowMatch        OBJECT IDENTIFIER ::= {id-kmr 1}
id-kmr-supplierConsumerMatch    OBJECT IDENTIFIER ::= {id-kmr 2}
id-kmr-supplierConsumersMatch   OBJECT IDENTIFIER ::= {id-kmr 3}

END -- DSAOperationalAttributeTypes

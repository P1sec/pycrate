LCSChargingDataTypes {itu-t (0) identified-organization (4) etsi(0) mobileDomain (0) charging (5) lcsChargingDataTypes (6) asn1Module (0) version2 (1)}

DEFINITIONS IMPLICIT TAGS	::=

BEGIN

-- EXPORTS everything

IMPORTS


IPAddress,
LCSClientIdentity,
LocalSequenceNumber,
ManagementExtensions,
MSISDN,
PLMN-Id,
PositioningData,
RecordingEntity,
RecordType,
TimeStamp
FROM GenericChargingDataTypes {itu-t (0) identified-organization (4) etsi(0) mobileDomain (0) charging (5) genericChargingDataTypes (0) asn1Module (0) version2 (1)}
Ext-GeographicalInformation,
LCSClientType,
LCS-Priority,
LocationType
FROM MAP-LCS-DataTypes {itu-t identified-organization (4) etsi (0) mobileDomain (0) gsm-Network (1) modules (3) map-LCS-DataTypes (25)  version18 (18) }
-- from TS 29.002 [214]

AddressString,
IMSI
FROM MAP-CommonDataTypes {itu-t identified-organization (4) etsi (0) mobileDomain (0) gsm-Network (1) modules (3) map-CommonDataTypes (18)  version18 (18) }
-- from TS 29.002 [214]

;

--
--  LCS RECORDS
--

LCSRecord	::= CHOICE
--
-- Record values 71..75 are LCS specific
--
{
	lCSGMORecord		[71] LCSGMORecord,
	lCSRGMTRecord		[72] LCSRGMTRecord,
	lCSHGMTRecord		[73] LCSHGMTRecord,
	lCSVGMTRecord		[74] LCSVGMTRecord,
	lCSGNIRecord		[75] LCSGNIRecord
}

LCSGMORecord	::= SET
{
	recordType					[0] RecordType,
	recordingEntity				[1] RecordingEntity,
	lcsClientType				[2] LCSClientType OPTIONAL,
	lcsClientIdentity			[3] LCSClientIdentity OPTIONAL,
	servedIMSI					[4] IMSI,
	servedMSISDN				[5] MSISDN OPTIONAL,
	servingEntity				[6] ServingEntity OPTIONAL,
	locationEstimate			[7] Ext-GeographicalInformation OPTIONAL,
	positioningData				[8] PositioningData OPTIONAL,
	userError					[9] UserError OPTIONAL,
	providerError				[10] ProviderError OPTIONAL,
	recordTimeStamp				[11] TimeStamp,
	localSequenceNumber			[12] LocalSequenceNumber OPTIONAL,
	recordExtensions			[13] ManagementExtensions OPTIONAL
}

LCSRGMTRecord	::= SET
{
	recordType					[0] RecordType,
	recordingEntity				[1] RecordingEntity,
	lcsClientType				[2] LCSClientType OPTIONAL,
	lcsClientIdentity			[3] LCSClientIdentity OPTIONAL,
	targetIMSI					[4] IMSI,
	targetMSISDN				[5] MSISDN OPTIONAL,
	locationType				[6] LocationType,
	lCSPriority					[7] LCS-Priority OPTIONAL,
	resultCode					[8] ResultCodeType OPTIONAL,
	recordTimeStamp				[9] TimeStamp,
	localSequenceNumber			[10] LocalSequenceNumber OPTIONAL,
	recordExtensions			[11] ManagementExtensions OPTIONAL,
	homeGMLCIdentity			[12] IPAddress OPTIONAL
}

LCSHGMTRecord	::= SET
{
	recordType					[0] RecordType,
	recordingEntity				[1] RecordingEntity,
	lcsClientType				[2] LCSClientType OPTIONAL,
	lcsClientIdentity			[3] LCSClientIdentity OPTIONAL,
	targetIMSI					[4] IMSI,
	targetMSISDN				[5] MSISDN OPTIONAL,
	locationType				[6] LocationType,
	lCSPriority					[7] LCS-Priority OPTIONAL,
	resultCode					[8] ResultCodeType OPTIONAL,
	recordTimeStamp				[9] TimeStamp,
	localSequenceNumber			[10] LocalSequenceNumber OPTIONAL,
	recordExtensions			[11] ManagementExtensions OPTIONAL,
	requestingGMLCIdentity		[12] IPAddress OPTIONAL,
	visitedGMLCIdentity			[13] IPAddress OPTIONAL,
	servingNetworkIdentity		[14] PLMN-Id OPTIONAL
}

LCSVGMTRecord	::= SET
{
	recordType					[0] RecordType,
	recordingEntity				[1] RecordingEntity,
	lcsClientType				[2] LCSClientType OPTIONAL,
	lcsClientIdentity			[3] LCSClientIdentity OPTIONAL,
	targetIMSI					[4] IMSI,
	targetMSISDN				[5] MSISDN OPTIONAL,
	locationType				[6] LocationType,
	lCSPriority					[7] LCS-Priority OPTIONAL,
	resultCode					[8] ResultCodeType OPTIONAL,
	recordTimeStamp				[9] TimeStamp,
	localSequenceNumber			[10] LocalSequenceNumber OPTIONAL,
	recordExtensions			[11] ManagementExtensions OPTIONAL,
	homeGMLCIdentity			[12] IPAddress OPTIONAL
}

LCSGNIRecord	::= SET
{
	recordType					[0] RecordType,
	recordingEntity				[1] RecordingEntity,
	lcsClientType				[2] LCSClientType OPTIONAL,
	lcsClientIdentity			[3] LCSClientIdentity OPTIONAL,
	servedIMSI					[4] IMSI,
	servedMSISDN				[5] MSISDN OPTIONAL,
	servingEntity				[6] ServingEntity OPTIONAL,
	resultCode					[7] ResultCodeType OPTIONAL,
	recordTimeStamp				[8] TimeStamp,
	localSequenceNumber			[9] LocalSequenceNumber OPTIONAL,
	recordExtensions			[10] ManagementExtensions OPTIONAL
}

--
--  LCS DATA TYPES
--

ProviderError	::= INTEGER
--
-- see ITU-T Q.733 [307] for invoke problem codes
--

ResultCodeType			::= INTEGER (0..MAX)
--
-- Result codes as defined in OMA-MLP Specifications [311]
--

ServingEntity ::= AddressString

UserError	::= OCTET STRING (SIZE (1))
--
-- see TS 29.002 [214] for error code values
--


END

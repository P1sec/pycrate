-- **************************************************************
--
-- Constant definitions
--
-- **************************************************************
XwAP-Constants {
itu-t (0) identified-organization (4) etsi (0) mobileDomain (0)
eps-Access (21) modules (3) xwap (8) version1 (1) xwap-Constants (4) }

DEFINITIONS AUTOMATIC TAGS ::=

BEGIN

-- **************************************************************
--
-- IE parameter types from other modules.
--
-- **************************************************************

IMPORTS
	ProcedureCode,
	ProtocolIE-ID

FROM XwAP-CommonDataTypes;


-- **************************************************************
--
-- Elementary Procedures
--
-- **************************************************************

id-xwSetup									ProcedureCode ::= 0
id-wTConfigurationUpdate					ProcedureCode ::= 1
id-wTStatusReportingInitiation				ProcedureCode ::= 2
id-wTStatusReporting						ProcedureCode ::= 3
id-errorIndication							ProcedureCode ::= 4
id-reset									ProcedureCode ::= 5
id-wTAdditionPreparation					ProcedureCode ::= 6
id-eNBInitiatedWTModification				ProcedureCode ::= 7
id-wTInitiatedWTModification				ProcedureCode ::= 8
id-eNBInitiatedWTRelease					ProcedureCode ::= 9
id-wTInitiatedWTRelease						ProcedureCode ::= 10
id-wTAssociationConfirmation				ProcedureCode ::= 11
id-privateMessage							ProcedureCode ::= 12
id-lWIPAdditionPreparation					ProcedureCode ::= 13
id-eNBInitiatedLWIPModification				ProcedureCode ::= 14
id-eNBInitiatedLWIPRelease					ProcedureCode ::= 15
id-wTInitiatedLWIPRelease					ProcedureCode ::= 16

-- **************************************************************
--
-- Extension constants
--
-- **************************************************************

maxPrivateIEs							INTEGER ::= 65535
maxProtocolExtensions					INTEGER ::= 65535
maxProtocolIEs							INTEGER ::= 65535


-- **************************************************************
--
-- Lists
--
-- **************************************************************

maxnoofBands								INTEGER ::= 256
maxnoofBearers								INTEGER ::= 256
maxnoofBSSs									INTEGER ::= 4096
maxnoofErrors								INTEGER ::= 256
maxnoofFailedMeasObjects					INTEGER ::= 32
maxnoofMobilitySetItems						INTEGER ::= 1024
maxnoofWLANIdentifierItems					INTEGER ::= 4096
maxnoofeNBNeighbours							INTEGER ::= 256


-- **************************************************************
--
-- IEs
--
-- **************************************************************

id-BSSMeasurementResult-Item							ProtocolIE-ID ::= 0
id-BSSMeasurementResult-List							ProtocolIE-ID ::= 1
id-BSSToReport-Item 									ProtocolIE-ID ::= 2
id-BSSToReport-List 									ProtocolIE-ID ::= 3
id-Cause 												ProtocolIE-ID ::= 4
id-CompleteFailureCauseInformation-Item 				ProtocolIE-ID ::= 5
id-CompleteFailureCauseInformation-List 				ProtocolIE-ID ::= 6
id-CriticalityDiagnostics 								ProtocolIE-ID ::= 7
id-ENB-Measurement-ID 									ProtocolIE-ID ::= 8
id-Global-ENB-ID 										ProtocolIE-ID ::= 9
id-MeasurementFailureCause-Item 						ProtocolIE-ID ::= 10
id-MeasurementInitiationResult-Item 					ProtocolIE-ID ::= 11
id-MeasurementInitiationResult-List 					ProtocolIE-ID ::= 12
id-PartialSuccessIndicator 								ProtocolIE-ID ::= 13
id-Registration-Request 								ProtocolIE-ID ::= 14
id-ReportCharacteristics 								ProtocolIE-ID ::= 15
id-ReportingPeriodicity 								ProtocolIE-ID ::= 16
id-WLANIdentifier-Item 									ProtocolIE-ID ::= 17
id-WLANIdentifier-List 									ProtocolIE-ID ::= 18
id-WLANIdentifiersToAdd-List 							ProtocolIE-ID ::= 19
id-WLANIdentifiersToDelete-Item 						ProtocolIE-ID ::= 20
id-WLANIdentifiersToDelete-List 						ProtocolIE-ID ::= 21
id-WLANIdentifiersToModify-List 						ProtocolIE-ID ::= 22
id-WTID 												ProtocolIE-ID ::= 23
id-WT-Measurement-ID 									ProtocolIE-ID ::= 24
id-ENB-UE-XwAP-ID										ProtocolIE-ID ::= 25
id-WT-UE-XwAP-ID										ProtocolIE-ID ::= 26
id-BSS-Item												ProtocolIE-ID ::= 27
id-E-RABs-ToBeAdded-List								ProtocolIE-ID ::= 28
id-E-RABs-ToBeAdded-Item								ProtocolIE-ID ::= 29
id-UE-Identity											ProtocolIE-ID ::= 30
id-WLANSecurityInfo										ProtocolIE-ID ::= 31
id-E-RABs-Admitted-ToBeAdded-List						ProtocolIE-ID ::= 32
id-E-RABs-Admitted-ToBeAdded-Item						ProtocolIE-ID ::= 33
id-E-RABs-NotAdmitted-List								ProtocolIE-ID ::= 34
id-E-RAB-Item											ProtocolIE-ID ::= 35
id-UE-ContextInformationWTModReq						ProtocolIE-ID ::= 36
id-E-RABs-ToBeAdded-ModReqItem							ProtocolIE-ID ::= 37
id-E-RABs-ToBeModified-ModReqItem						ProtocolIE-ID ::= 38
id-E-RABs-ToBeReleased-ModReqItem						ProtocolIE-ID ::= 39
id-E-RABs-Admitted-ToBeAdded-ModAckList					ProtocolIE-ID ::= 40
id-E-RABs-Admitted-ToBeAdded-ModAckItem					ProtocolIE-ID ::= 41
id-E-RABs-Admitted-ToBeModified-ModAckList				ProtocolIE-ID ::= 42
id-E-RABs-Admitted-ToBeModified-ModAckItem				ProtocolIE-ID ::= 43
id-E-RABs-Admitted-ToBeReleased-ModAckList				ProtocolIE-ID ::= 44
id-E-RABs-Admitted-ToBeReleased-ModAckItem				ProtocolIE-ID ::= 45
id-E-RABs-ToBeReleased-ModReqdList						ProtocolIE-ID ::= 46
id-E-RABs-ToBeReleased-ModReqdItem						ProtocolIE-ID ::= 47
id-E-RABs-ToBeReleased-List-RelReq						ProtocolIE-ID ::= 48
id-E-RABs-ToBeReleased-RelReqItem						ProtocolIE-ID ::= 49
id-E-RABs-ToBeReleased-List-RelConf						ProtocolIE-ID ::= 50
id-E-RABs-ToBeReleased-RelConfItem						ProtocolIE-ID ::= 51
id-E-RABs-Confirmed-ToBeReleased-ModReqdList			ProtocolIE-ID ::= 52
id-E-RABs-Confirmed-ToBeReleased-ModReqdItem			ProtocolIE-ID ::= 53
id-MobilitySet											ProtocolIE-ID ::= 54
id-ServingPLMN											ProtocolIE-ID ::= 55
id-E-RABs-ToBeModified-ModReqdList						ProtocolIE-ID ::= 56
id-E-RABs-ToBeModified-ModReqdItem						ProtocolIE-ID ::= 57
id-E-RABs-Confirmed-ToBeModified-ModReqdList			ProtocolIE-ID ::= 58
id-E-RABs-Confirmed-ToBeModified-ModReqdItem			ProtocolIE-ID ::= 59
id-wLANBandInformation									ProtocolIE-ID ::= 60
id-WLANIdentifiersToDeleteExtension-Item 				ProtocolIE-ID ::= 61
id-WLANIdentifiersToDeleteExtension-List 				ProtocolIE-ID ::= 62
id-TimeToWait											ProtocolIE-ID ::= 63
id-UE-ContextKeptIndicator								ProtocolIE-ID ::= 64
id-DRB-Identity											ProtocolIE-ID ::= 65
id-LWA-WLAN-AC											ProtocolIE-ID ::= 66
id-eNBNeighbour-List									ProtocolIE-ID ::= 67
id-eNBNeighbour-Item									ProtocolIE-ID ::= 68
id-LWIP-SeGWSecurityInfo								ProtocolIE-ID ::= 69
id-eNBGTPtunnelEndpoint									ProtocolIE-ID ::= 70
id-LWIP-SeGWGTPtunnelEndpoint							ProtocolIE-ID ::= 71
id-WLANUsage											ProtocolIE-ID ::= 72
id-WT-MAC-Address										ProtocolIE-ID ::= 73

END

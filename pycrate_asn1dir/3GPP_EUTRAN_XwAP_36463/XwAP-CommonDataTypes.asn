-- **************************************************************
--
-- Common definitions
--
-- **************************************************************

XwAP-CommonDataTypes {
itu-t (0) identified-organization (4) etsi (0) mobileDomain (0)
eps-Access (21) modules (3) xwap (8) version1 (1) xwap-CommonDataTypes (3) }

DEFINITIONS AUTOMATIC TAGS ::=

BEGIN

-- **************************************************************
--
-- IE parameter types from other modules.
--
-- **************************************************************

IMPORTS
	maxPrivateIEs,
	maxProtocolExtensions,
	maxProtocolIEs

FROM XwAP-Constants;

-- **************************************************************
--
-- Common Data Types
--
-- **************************************************************

Criticality ::= ENUMERATED { reject, ignore, notify }

Presence ::= ENUMERATED { optional, conditional, mandatory }

PrivateIE-ID ::= CHOICE {
	local				INTEGER (0.. maxPrivateIEs),
	global				OBJECT IDENTIFIER
}

ProcedureCode ::= INTEGER (0..255)

ProtocolExtensionID ::= INTEGER (0.. maxProtocolExtensions)

ProtocolIE-ID ::= INTEGER (0.. maxProtocolIEs)

TriggeringMessage ::= ENUMERATED { initiating-message, successful-outcome, unsuccessful-outcome }
END

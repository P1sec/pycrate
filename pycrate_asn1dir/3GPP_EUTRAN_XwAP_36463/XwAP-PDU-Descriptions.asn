-- **************************************************************
--
-- Elementary Procedure definitions for XwAP
--
-- **************************************************************

XwAP-PDU-Descriptions  {
itu-t (0) identified-organization (4) etsi (0) mobileDomain (0)
eps-Access (21) modules (3) xwap (8) version1 (1) xwap-PDU-Descriptions (0)}

DEFINITIONS AUTOMATIC TAGS ::=

BEGIN

-- **************************************************************
--
-- IE parameter types from other modules
--
-- **************************************************************

IMPORTS
	Criticality,
	ProcedureCode

FROM XwAP-CommonDataTypes


	ErrorIndication,
	LWIPAdditionRequest,
	LWIPAdditionRequestAcknowledge,
	LWIPAdditionRequestReject,
	LWIPModificationRequest,
	LWIPModificationRequestAcknowledge,
	LWIPModificationRequestReject,
	LWIPReleaseRequest,
	LWIPReleaseRequired,
	LWIPReleaseConfirm,
	PrivateMessage,
	Reset,
	ResetResponse,
	XwSetupRequest,
	XwSetupResponse,
	XwSetupFailure,
	WTAdditionRequest,
	WTAdditionRequestAcknowledge,
	WTAdditionRequestReject,
	WTAssociationConfirmation,
	WTConfigurationUpdate,
	WTConfigurationUpdateAcknowledge,
	WTConfigurationUpdateFailure,
	WTModificationRequest,
	WTModificationRequestAcknowledge,
	WTModificationRequestReject,
	WTModificationRequired,
	WTModificationConfirm,
	WTModificationRefuse,
	WTReleaseRequest,
	WTReleaseRequired,
	WTReleaseConfirm,
	WTStatusRequest,
	WTStatusResponse,
	WTStatusFailure,
	WTStatusReport

FROM XwAP-PDU-Contents

	id-eNBInitiatedWTModification,
	id-eNBInitiatedWTRelease,
	id-errorIndication,
	id-privateMessage,
	id-reset,
	id-xwSetup,
	id-wTAdditionPreparation,
	id-wTAssociationConfirmation,
	id-wTConfigurationUpdate,
	id-wTInitiatedWTModification,
	id-wTInitiatedWTRelease,
	id-wTStatusReporting,
	id-wTStatusReportingInitiation,
	id-lWIPAdditionPreparation,
	id-eNBInitiatedLWIPModification,
	id-eNBInitiatedLWIPRelease,
	id-wTInitiatedLWIPRelease

FROM XwAP-Constants;


-- **************************************************************
--
-- Interface Elementary Procedure Class
--
-- **************************************************************

XWAP-ELEMENTARY-PROCEDURE ::= CLASS {
	&InitiatingMessage				,
	&SuccessfulOutcome							OPTIONAL,
	&UnsuccessfulOutcome						OPTIONAL,
	&procedureCode				ProcedureCode	UNIQUE,
	&criticality				Criticality		DEFAULT ignore
}
WITH SYNTAX {
	INITIATING MESSAGE			&InitiatingMessage
	[SUCCESSFUL OUTCOME			&SuccessfulOutcome]
	[UNSUCCESSFUL OUTCOME		&UnsuccessfulOutcome]
	PROCEDURE CODE				&procedureCode
	[CRITICALITY				&criticality]
}

-- **************************************************************
--
-- Interface PDU Definition
--
-- **************************************************************

XwAP-PDU ::= CHOICE {
	initiatingMessage	InitiatingMessage,
	successfulOutcome	SuccessfulOutcome,
	unsuccessfulOutcome	UnsuccessfulOutcome,
	...
}

InitiatingMessage ::= SEQUENCE {
	procedureCode	XWAP-ELEMENTARY-PROCEDURE.&procedureCode		({XWAP-ELEMENTARY-PROCEDURES}),
	criticality		XWAP-ELEMENTARY-PROCEDURE.&criticality			({XWAP-ELEMENTARY-PROCEDURES}{@procedureCode}),
	value			XWAP-ELEMENTARY-PROCEDURE.&InitiatingMessage	({XWAP-ELEMENTARY-PROCEDURES}{@procedureCode})
}

SuccessfulOutcome ::= SEQUENCE {
	procedureCode	XWAP-ELEMENTARY-PROCEDURE.&procedureCode		({XWAP-ELEMENTARY-PROCEDURES}),
	criticality		XWAP-ELEMENTARY-PROCEDURE.&criticality			({XWAP-ELEMENTARY-PROCEDURES}{@procedureCode}),
	value			XWAP-ELEMENTARY-PROCEDURE.&SuccessfulOutcome	({XWAP-ELEMENTARY-PROCEDURES}{@procedureCode})
}

UnsuccessfulOutcome ::= SEQUENCE {
	procedureCode	XWAP-ELEMENTARY-PROCEDURE.&procedureCode		({XWAP-ELEMENTARY-PROCEDURES}),
	criticality		XWAP-ELEMENTARY-PROCEDURE.&criticality			({XWAP-ELEMENTARY-PROCEDURES}{@procedureCode}),
	value			XWAP-ELEMENTARY-PROCEDURE.&UnsuccessfulOutcome	({XWAP-ELEMENTARY-PROCEDURES}{@procedureCode})
}

-- **************************************************************
--
-- Interface Elementary Procedure List
--
-- **************************************************************

XWAP-ELEMENTARY-PROCEDURES XWAP-ELEMENTARY-PROCEDURE ::= {
	XWAP-ELEMENTARY-PROCEDURES-CLASS-1			|
	XWAP-ELEMENTARY-PROCEDURES-CLASS-2,
	...
}


XWAP-ELEMENTARY-PROCEDURES-CLASS-1 XWAP-ELEMENTARY-PROCEDURE ::= {
	xwSetup							|
	wTConfigurationUpdate			|
	wTStatusReportingInitiation		|
	reset							|
	wTAdditionPreparation			|
	eNBInitiatedWTModification		|
	wTInitiatedWTModification		|
	wTInitiatedWTRelease			|
	lWIPAdditionPreparation			|
	eNBInitiatedLWIPModification				|
	wTInitiatedLWIPRelease			,

	...
}

XWAP-ELEMENTARY-PROCEDURES-CLASS-2 XWAP-ELEMENTARY-PROCEDURE ::= {
	wTStatusReporting				|
	errorIndication					|
	eNBInitiatedWTRelease			|
	wTAssociationConfirmation		|
	privateMessage					|
	eNBInitiatedLWIPRelease			,
	...
}

-- **************************************************************
--
-- Interface Elementary Procedures
--
-- **************************************************************

xwSetup 					XWAP-ELEMENTARY-PROCEDURE ::= {
	INITIATING MESSAGE		XwSetupRequest
	SUCCESSFUL OUTCOME		XwSetupResponse
	UNSUCCESSFUL OUTCOME	XwSetupFailure
	PROCEDURE CODE			id-xwSetup
	CRITICALITY				reject
}

wTConfigurationUpdate 		XWAP-ELEMENTARY-PROCEDURE ::= {
	INITIATING MESSAGE		WTConfigurationUpdate
	SUCCESSFUL OUTCOME		WTConfigurationUpdateAcknowledge
	UNSUCCESSFUL OUTCOME 	WTConfigurationUpdateFailure
	PROCEDURE CODE			id-wTConfigurationUpdate
	CRITICALITY				reject
}

wTStatusReportingInitiation	XWAP-ELEMENTARY-PROCEDURE ::= {
	INITIATING MESSAGE		WTStatusRequest
	SUCCESSFUL OUTCOME		WTStatusResponse
	UNSUCCESSFUL OUTCOME	WTStatusFailure
	PROCEDURE CODE			id-wTStatusReportingInitiation
	CRITICALITY				reject
}

wTStatusReporting 			XWAP-ELEMENTARY-PROCEDURE ::= {
	INITIATING MESSAGE		WTStatusReport
	PROCEDURE CODE			id-wTStatusReporting
	CRITICALITY				ignore
}

errorIndication				XWAP-ELEMENTARY-PROCEDURE ::= {
	INITIATING MESSAGE		ErrorIndication
	PROCEDURE CODE			id-errorIndication
	CRITICALITY				ignore
}

reset						XWAP-ELEMENTARY-PROCEDURE ::= {
	INITIATING MESSAGE		Reset
	SUCCESSFUL OUTCOME		ResetResponse
	PROCEDURE CODE			id-reset
	CRITICALITY				reject
}

wTAdditionPreparation 		XWAP-ELEMENTARY-PROCEDURE ::= {
	INITIATING MESSAGE		WTAdditionRequest
	SUCCESSFUL OUTCOME		WTAdditionRequestAcknowledge
	UNSUCCESSFUL OUTCOME 	WTAdditionRequestReject
	PROCEDURE CODE			id-wTAdditionPreparation
	CRITICALITY				reject
}

eNBInitiatedWTModification	XWAP-ELEMENTARY-PROCEDURE ::= {
	INITIATING MESSAGE		WTModificationRequest
	SUCCESSFUL OUTCOME		WTModificationRequestAcknowledge
	UNSUCCESSFUL OUTCOME 	WTModificationRequestReject
	PROCEDURE CODE			id-eNBInitiatedWTModification
	CRITICALITY				reject
}

wTInitiatedWTModification	XWAP-ELEMENTARY-PROCEDURE ::= {
	INITIATING MESSAGE		WTModificationRequired
	SUCCESSFUL OUTCOME		WTModificationConfirm
	UNSUCCESSFUL OUTCOME 	WTModificationRefuse
	PROCEDURE CODE			id-wTInitiatedWTModification
	CRITICALITY				reject
}

eNBInitiatedWTRelease		XWAP-ELEMENTARY-PROCEDURE ::= {
	INITIATING MESSAGE		WTReleaseRequest
	PROCEDURE CODE			id-eNBInitiatedWTRelease
	CRITICALITY				ignore
}

wTInitiatedWTRelease		XWAP-ELEMENTARY-PROCEDURE ::= {
	INITIATING MESSAGE		WTReleaseRequired
	SUCCESSFUL OUTCOME		WTReleaseConfirm
	PROCEDURE CODE			id-wTInitiatedWTRelease
	CRITICALITY				reject
}

wTAssociationConfirmation	XWAP-ELEMENTARY-PROCEDURE ::= {
	INITIATING MESSAGE		WTAssociationConfirmation
	PROCEDURE CODE			id-wTAssociationConfirmation
	CRITICALITY				ignore
}

privateMessage				XWAP-ELEMENTARY-PROCEDURE ::= {
	INITIATING MESSAGE		PrivateMessage
	PROCEDURE CODE			id-privateMessage
	CRITICALITY				ignore
}

lWIPAdditionPreparation		XWAP-ELEMENTARY-PROCEDURE ::= {
	INITIATING MESSAGE		LWIPAdditionRequest
	SUCCESSFUL OUTCOME		LWIPAdditionRequestAcknowledge
	UNSUCCESSFUL OUTCOME	LWIPAdditionRequestReject
	PROCEDURE CODE			id-lWIPAdditionPreparation
	CRITICALITY				reject
}
eNBInitiatedLWIPModification	XWAP-ELEMENTARY-PROCEDURE ::= {
	INITIATING MESSAGE			LWIPModificationRequest
	SUCCESSFUL OUTCOME			LWIPModificationRequestAcknowledge
	UNSUCCESSFUL OUTCOME 		LWIPModificationRequestReject
	PROCEDURE CODE				id-eNBInitiatedLWIPModification
	CRITICALITY					reject
}

eNBInitiatedLWIPRelease		XWAP-ELEMENTARY-PROCEDURE ::= {
	INITIATING MESSAGE		LWIPReleaseRequest
	PROCEDURE CODE			id-eNBInitiatedLWIPRelease
	CRITICALITY				ignore
}

wTInitiatedLWIPRelease		XWAP-ELEMENTARY-PROCEDURE ::= {
	INITIATING MESSAGE		LWIPReleaseRequired
	SUCCESSFUL OUTCOME		LWIPReleaseConfirm
	PROCEDURE CODE			id-wTInitiatedLWIPRelease
	CRITICALITY				reject
}

END
